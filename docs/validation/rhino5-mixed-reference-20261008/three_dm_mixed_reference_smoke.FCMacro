"""Actual host lifecycle of mixed PolyCurve native references and target losses."""
import FreeCAD as App,FreeCADGui as Gui
from PySide6 import QtCore
from pathlib import Path
import os,json,hashlib,traceback
out=Path(os.environ['OM9_SMOKE_OUTPUT']);result={'checks':[]}
def sha(p):return hashlib.sha256(p.read_bytes()).hexdigest()
def check(name,value):
    result['checks'].append(dict(name=name,passed=bool(value)))
    (out/'progress.json').write_text(json.dumps(result,indent=2))
    if not value:raise AssertionError(name)
def run():
    try:
        import ThreeDm,OpenMatrix9Gui as native
        root=Path('H:/FreeCAD-src/build/om9-dev/docs/validation/rhino5-mixed-reference-20261008')
        oracle=json.loads((root/'oracle.json').read_text());proof=json.loads((root/'rhino5-gui-profile-results.json').read_text())
        check('actual Rhino6 target failures bind source oracle and probe',not proof['ok'] and len(proof['cases'])==len(oracle['cases'])==6 and proof['oracle_sha256']==sha(root/'oracle.json') and proof['probe_sha256']==sha(root/'rhino5-mixed-reference-gui-probe.py'))
        for expected,row in zip(oracle['cases'],proof['cases']):
            uuid=expected['objects'][1]['uuid'];owner_id=expected['objects'][0]['uuid']
            for source in [root/row['fixture'],root/Path(row['saved_fixture']).name]:
                label=source.name;manifest=json.loads(native.inspect3dm(str(source)));record=next(r for r in manifest['records'] if r['source_uuid']==uuid)
                check(label+' complete typed parent/child owner closure retained',record['class_name']=='ON_PolyCurve' and record['capability']=='retained' and record['poly_edge_native']['object_references']==[owner_id] and owner_id in record['dependencies'])
                broken=label.startswith('gui-resaved-') and 'reversed-1' in label
                if broken:
                    check(label+' saved direction loss is explicit invalid native graph',record['native_reference_analysis']['status']=='invalid' and bool(manifest['issues']))
                    doc=App.newDocument('BrokenMixedRef');sentinel=doc.addObject('App::FeaturePython','Unchanged');sentinel.Label='preserve-existing';names=[o.Name for o in doc.Objects];error=''
                    try:ThreeDm.import_file(str(source),doc,mode='preserve')
                    except Exception as exc:error=str(exc)
                    check(label+' corrupt SaveAs import refuses without changing document',bool(error) and [o.Name for o in doc.Objects]==names and sentinel.Label=='preserve-existing')
                    App.closeDocument(doc.Name);continue
                check(label+' bounded native owner graph is linked with no issues',not manifest['issues'] and record['native_reference_analysis']['status']=='linked')
                external=out/label;external.write_bytes(source.read_bytes());doc=App.newDocument('MixedRef')
                objects=ThreeDm.import_file(str(external),doc,mode='preserve');by_id={json.loads(o.OM9SourceRecord)['source_uuid']:o for o in objects};obj=by_id[uuid];baseline=obj.OM9SourceRecord;name=obj.Name
                check(label+' public preservation import retains exact parent and independent editable owner',len(objects)==2 and owner_id in by_id and json.loads(baseline)==record and obj.OM9Capability=='retained' and not hasattr(obj,'Shape'))
                protected=out/(label+'-protected.3dm');protected.write_bytes(b'keep-target');count=len(doc.Objects);error=''
                try:ThreeDm.export_file(str(protected),[obj])
                except Exception as exc:error=str(exc)
                check(label+' selected unsafe V5 export is refused atomically',bool(error) and ('nested PolyEdge' in error or 'Opaque plugin table dependencies' in error) and protected.read_bytes()==b'keep-target' and len(doc.Objects)==count and obj.OM9SourceRecord==baseline)
                project=out/(label+'.FCStd');doc.saveAs(str(project));external.unlink();App.closeDocument(doc.Name);doc=App.openDocument(str(project));obj=doc.getObject(name)
                check(label+' FCStd survives source deletion with exact archive/tree',sha(Path(obj.OM9ArchiveOwner.OM9SourceArchive))==sha(source) and obj.OM9SourceRecord==baseline)
                restored=next(r for r in json.loads(native.inspect3dm(obj.OM9ArchiveOwner.OM9SourceArchive))['records'] if r['source_uuid']==uuid)
                check(label+' reopened graph/owner dependencies/CRC remain exact',restored['native_reference_analysis']['status']=='linked' and restored['poly_edge_native']==record['poly_edge_native'] and restored['dependencies']==record['dependencies'] and restored['geometry_crc']==record['geometry_crc'])
                App.closeDocument(doc.Name)
        result.update(ok=True,rhino_report_sha256=sha(root/'rhino5-gui-profile-results.json'),full_exchange_complete=False)
    except Exception:result.update(ok=False,error=traceback.format_exc())
    (out/'results.json').write_text(json.dumps(result,indent=2))
    for name in list(App.listDocuments()):App.closeDocument(name)
    QtCore.QTimer.singleShot(100,Gui.getMainWindow().close)
QtCore.QTimer.singleShot(1000,run)
