"""Decode the actual Rhino-written nested sources before expanding target policy."""
import FreeCAD as App, FreeCADGui as Gui
from PySide6 import QtCore
from pathlib import Path
import json,os,hashlib,traceback
out=Path(os.environ['OM9_SMOKE_OUTPUT']);result={'checks':[]}
def sha(path):return hashlib.sha256(path.read_bytes()).hexdigest()
def check(name,value):
    result['checks'].append(dict(name=name,passed=bool(value)))
    if not value:raise AssertionError(name)
def run():
    try:
        import ThreeDm,OpenMatrix9Gui as native
        root=Path('H:/FreeCAD-src/build/om9-dev/docs/validation/rhino5-nested-profiles-20261007')
        proof=json.loads((root/'rhino5-exchange-profile-results.json').read_text());oracle=json.loads((root/'oracle.json').read_text())
        check('actual Rhino nested probe bound to native oracle and untouched active document',proof['ok'] and proof['active_document_untouched'] and len(proof['cases'])==len(oracle['cases'])==6 and proof['oracle_sha256']==sha(root/'oracle.json'))
        for expected,row in zip(oracle['cases'],proof['cases']):
            source=root/row['fixture'];saved=root/row['saved_fixture'];label=source.name
            check(label+' exact source and actual Rhino output bindings',expected['fixture']==row['fixture'] and sha(source)==row['source_sha256']==expected['source_sha256'] and sha(saved)==row['saved_sha256'] and row['passed'] and row['input_unchanged'])
            before=json.loads(native.inspect3dm(str(source)));after=json.loads(native.inspect3dm(str(saved)))
            a,b=before['records'][0],after['records'][0]
            check(label+' decoded UUID, class and full nested UV tree retained',after['source_version']==50 and not after['issues'] and len(after['records'])==1 and a['class_name']==b['class_name']=='ON_CurveOnSurface' and a['source_uuid']==b['source_uuid']==expected['objects'][0]['uuid'] and a['curve_on_surface_native']==b['curve_on_surface_native'] and a['dependencies']==b['dependencies'] and a['geometry_crc']==b['geometry_crc'])
            external=out/saved.name;external.write_bytes(saved.read_bytes());doc=App.newDocument('RhinoNested')
            obj=ThreeDm.import_file(str(external),doc,mode='preserve')[0];baseline=obj.OM9SourceRecord;name=obj.Name
            check(label+' retained host record keeps decoded child fields',json.loads(baseline)['curve_on_surface_native']==b['curve_on_surface_native'] and obj.OM9Capability=='retained')
            archive=out/(label+'.FCStd');doc.saveAs(str(archive));external.unlink();App.closeDocument(doc.Name)
            doc=App.openDocument(str(archive));obj=doc.getObject(name)
            check(label+' source-deleted FCStd retains exact actual Rhino archive and native children',sha(Path(obj.OM9ArchiveOwner.OM9SourceArchive))==row['saved_sha256'] and obj.OM9SourceRecord==baseline)
            App.closeDocument(doc.Name)
        result['rhino_report_sha256']=sha(root/'rhino5-exchange-profile-results.json');result['ok']=True
    except Exception:result.update(ok=False,error=traceback.format_exc())
    (out/'results.json').write_text(json.dumps(result,indent=2))
    for name in list(App.listDocuments()):App.closeDocument(name)
    QtCore.QTimer.singleShot(100,Gui.getMainWindow().close)
QtCore.QTimer.singleShot(1000,run)
