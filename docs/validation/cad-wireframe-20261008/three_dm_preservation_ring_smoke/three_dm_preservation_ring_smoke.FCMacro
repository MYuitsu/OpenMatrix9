import FreeCAD as App, FreeCADGui as Gui
from PySide6 import QtCore
from pathlib import Path
import os,json,traceback,hashlib
out=Path(os.environ['OM9_SMOKE_OUTPUT']);result={'checks':[]}
def check(name,value):
    result['checks'].append({'name':name,'passed':bool(value)})
    if not value:raise AssertionError(name)
def run():
    try:
        Gui.activateWorkbench('OpenMatrix9Workbench')
        import ThreeDm,ThreeDmArchiveState as state,OpenMatrix9Gui as native
        for filename in ['Oval-twist-ring.3dm','Oval-twist-ring-fixed.3dm']:
            source=Path(__file__).parent/'fixtures/3dm'/filename
            manifest=json.loads(native.inspect3dm(str(source)))
            doc=App.newDocument('PreservedRing')
            objects=ThreeDm.import_file(str(source),doc,mode='preserve')
            expected={r['source_uuid'] for r in manifest['records'] if r['role']=='top-level'}
            check(filename+' original identity graph',{o.OM9SourceUUID for o in objects}==expected)
            check(filename+' valid CAD',all(o.Shape.isValid() for o in objects if o.isDerivedFrom('Part::Feature')))
            container=next(o for o in doc.Objects if hasattr(o,'OM9SourceArchive'))
            check(filename+' complete manifest',json.loads(container.OM9ArchiveManifest)==manifest)
            check(filename+' exact snapshot',hashlib.sha256(Path(container.OM9SourceArchive).read_bytes()).hexdigest()==hashlib.sha256(source.read_bytes()).hexdigest())
            destination=out/(filename+'.FCStd');doc.saveAs(str(destination));App.closeDocument(doc.Name);doc=App.openDocument(str(destination))
            container=next(o for o in doc.Objects if hasattr(o,'OM9SourceArchive'));check(filename+' snapshot reopened',state.load_archive_state(container)['manifest']==manifest)
            App.closeDocument(doc.Name)
        result['ok']=True
    except Exception:result['ok']=False;result['error']=traceback.format_exc()
    (out/'results.json').write_text(json.dumps(result,indent=2))
    QtCore.QTimer.singleShot(100,Gui.getMainWindow().close)
QtCore.QTimer.singleShot(1000,run)
