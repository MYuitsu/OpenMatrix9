import os,json,traceback,subprocess
from pathlib import Path
import FreeCAD as App,FreeCADGui as Gui,Part
from PySide6 import QtCore
out=Path(os.environ['OM9_SMOKE_OUTPUT']);report={'checks':[]}
def check(n,v):
    report['checks'].append({'name':n,'passed':bool(v)})
    if not v:raise AssertionError(n)
def run():
    try:
        import ThreeDm,OpenMatrix9Gui as native
        Gui.activateWorkbench('OpenMatrix9Workbench');doc=App.newDocument('StockWorker')
        ring=doc.addObject('Part::Feature','Ring');ring.Shape=Part.makeTorus(10,1)
        curve=doc.addObject('Part::Feature','Curve');curve.Shape=Part.makeCircle(2);doc.recompute()
        source=out/'current.3dm';ThreeDm.export_file(str(source),[ring,curve],modeling=True)
        direct=out/'direct';direct.mkdir();expected=json.loads(native.prepareModeling3dm(str(source),str(direct),0))
        worker=Path(native.__file__).parent/'OM9ThreeDmImportWorker.exe';stage=out/'worker';stage.mkdir()
        req=out/'request.json';res=out/'worker.json'
        ids=sorted({item['root_uuid'] for item in expected['items']})
        check('worker request uses two inspected source roots',len(ids)==2 and all(len(value)==36 for value in ids))
        request=dict(source=str(source),staging=str(stage),scale=0,working=True,members=False,ids=ids)
        req.write_text(json.dumps(request),encoding='utf8')
        proc=subprocess.run([str(worker),str(req),str(res)],capture_output=True,timeout=90)
        report['worker_exit']=proc.returncode
        (out/'worker.stderr.log').write_bytes(proc.stderr)
        check('plugin-local worker runs with only installed host DLL search path',proc.returncode==0 and res.is_file())
        actual=json.loads(res.read_text(encoding='utf8'))
        check('worker imports same current object count',len(actual['rows'])==len(expected['items'])==2)
        def identity(item):
            return tuple(json.dumps(item[key],sort_keys=True) for key in ('name','source_uuid','root_uuid','geometry_kind','class_name','color','visible','locked'))
        check('worker preserves current source identity and attributes',sorted(map(identity,actual['rows']))==sorted(map(identity,expected['items'])))
        direct_shapes={item['source_uuid']:item for item in expected['items']}
        for item in actual['rows']:
            shape=Part.Shape();shape.read(item['brep']);check('worker stages valid editable BRep '+item['name'],shape.isValid())
            reference=Part.Shape();reference.read(direct_shapes[item['source_uuid']]['brep'])
            check('worker matches direct native geometry '+item['name'],abs(shape.Volume-reference.Volume)<1e-9 and abs(shape.Area-reference.Area)<1e-9 and abs(shape.Length-reference.Length)<1e-9)
        report.update(ok=True,module=native.__file__)
    except Exception:report.update(ok=False,error=traceback.format_exc())
    finally:
        (out/'results.json').write_text(json.dumps(report,indent=2),encoding='utf8')
        for n in list(App.listDocuments()):App.closeDocument(n)
        QtCore.QTimer.singleShot(100,Gui.getMainWindow().close)
QtCore.QTimer.singleShot(1000,run)
