# SPDX-License-Identifier: LGPL-2.1-or-later
"""Recorded replay result survives real Undo/Redo and a separate cold FCStd host."""
import json,math,os,traceback
from pathlib import Path
import FreeCAD as App,FreeCADGui as Gui,Part,Points,OpenMatrix9Gui as OM
from PySide6 import QtCore,QtGui,QtWidgets
out=Path(os.environ['OM9_SMOKE_OUTPUT']);report=dict(module=OM.__file__,checks=[],observations=[])
def check(name,value):report['checks'].append(dict(name=name,passed=bool(value)))
def enter(console,text):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier))
def settle():
 loop=QtCore.QEventLoop();QtCore.QTimer.singleShot(80,loop.quit);loop.exec()
def paired(child,kind,n):
 try:
  result=json.loads(child.OM9GeometryResult);snapshot=result['output_snapshots'][0];master=Part.Shape();master.importBrepFromString(snapshot['geometry_data']['native_master']['payload'])
  center=App.Vector()if kind=='Cloud'else App.Vector(5*n,0,0)if kind=='Around'else App.Vector(3*n,4*n,5*n);radius=n if kind=='Cloud'else 2
  if kind=='Deformable':
   context=result['operation_context'];plan=context.get('resolved_plan',context.get('construction',{}).get('circle',{}))
   if abs(plan['radius']-radius)>1e-7 or (App.Vector(*plan['center'])-center).Length>1e-7:return False
   if not all(not s.isNull()and s.isValid()and s.isClosed()and isinstance(s.Edges[0].Curve,Part.BSplineCurve)and s.Edges[0].Curve.isPeriodic()for s in [child.Shape,master]):return False
   for f in [0,.1,.3,.7,1]:
    a,b=child.Shape.Edges[0],master.Edges[0]
    if (a.valueAt(a.FirstParameter+f*(a.LastParameter-a.FirstParameter))-b.valueAt(b.FirstParameter+f*(b.LastParameter-b.FirstParameter))).Length>1e-7:return False
  elif not all(not s.isNull()and s.isValid()and s.isClosed()and isinstance(s.Edges[0].Curve,Part.Circle)and (s.Edges[0].Curve.Center-center).Length<1e-7 and abs(s.Edges[0].Curve.Radius-radius)<1e-7 for s in [child.Shape,master]):return False
  return snapshot['unit_context_snapshot']==child.OM9UnitContext and bool(result['input_snapshots'])
 except (ValueError,KeyError,IndexError,TypeError):return False
def assign(source,kind,n):
 if kind=='Cloud':source.Points=Points.Points([App.Vector(n,0,0),App.Vector(0,n,0),App.Vector(-n,0,0)])
 elif kind=='Around':source.Shape=Part.makeLine(App.Vector(),App.Vector(10*n,0,0))
 else:source.Shape=Part.Vertex(App.Vector(3*n,4*n,5*n))
def writer(console,kind):
 doc=App.newDocument('CircleHistoryRoundtrip'+kind)
 try:
  doc.UndoMode=1;OM.setUnitContext(doc.Name,1.,1.,.01,.001,.01);settings=doc.addObject('OpenMatrix9Gui::HistorySettings','OM9HistorySettings');settings.BrokenHistoryWarning=False
  source=doc.addObject('Points::Feature'if kind=='Cloud'else 'Part::Feature','Source');assign(source,kind,1);doc.recompute();args=['Circle','History=Yes']
  if kind=='Deformable':args+=['Deformable=Yes']
  if kind=='Cloud':Gui.Selection.clearSelection();Gui.Selection.addSelection(source);args+=['FitPoints','Selection','']
  elif kind=='Around':args+=['AroundCurve','Curve=Source.Edge1','OnCurve=.5','Radius=2']
  else:args+=['Point=Source.Vertex1','Radius=2']
  for text in args:enter(console,text)
  settle();child=doc.getObject('Circle');check(kind+' initial paired result',paired(child,kind,1))
  assign(source,kind,2);doc.recompute();settle();check(kind+' replay paired at source2',paired(child,kind,2))
  doc.openTransaction('Move Circle History source');assign(source,kind,3);doc.commitTransaction();doc.recompute();settle();check(kind+' booked source3 replay paired',paired(child,kind,3))
  doc.undo();doc.recompute();settle();check(kind+' real Undo restores source2 and recomputes pair',paired(child,kind,2))
  doc.redo();doc.recompute();settle();check(kind+' real Redo executes source3 pair',paired(child,kind,3))
  archive=out/(kind+'.FCStd');doc.saveAs(str(archive));raw=child.OM9GeometryResult
  (out/(kind+'.json')).write_text(json.dumps(dict(raw=raw,kind=kind,n=3)),encoding='utf-8');check(kind+' recorded links persist with paired saved evidence',child.Recorded and bool(child.Sources or child.SourceCurve)and bool(raw))
  report['observations'].append(dict(case=kind,status=child.getStatusString(),archive=str(archive)))
 finally:enter(console,'Cancel');App.closeDocument(doc.Name)
def reader(kind):
 directory=Path(os.environ['OM9_HISTORY_ARCHIVES']);evidence=json.loads((directory/(kind+'.json')).read_text());doc=App.openDocument(str(directory/(kind+'.FCStd')))
 try:
  settle();child=doc.getObject('Circle');check(kind+' cold saved raw result bytes retained',child.OM9GeometryResult==evidence['raw'])
  check(kind+' cold independently decoded current CAD paired',child.Recorded and paired(child,kind,3))
  assign(doc.getObject('Source'),kind,4);doc.recompute();settle();check(kind+' cold restored recipe replays source4 pair',paired(child,kind,4))
  report['observations'].append(dict(case=kind,status=child.getStatusString()))
 finally:App.closeDocument(doc.Name)
def run():
 try:
  Gui.activateWorkbench('OpenMatrix9Workbench');settle();console=Gui.getMainWindow().findChild(QtWidgets.QPlainTextEdit,'OM9CommandTranscript')
  for kind in ['Center','Around','Cloud','Deformable']:
   if os.environ.get('OM9_HISTORY_ARCHIVES'):reader(kind)
   else:writer(console,kind)
  report['ok']=all(c['passed']for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
