# SPDX-License-Identifier: LGPL-2.1-or-later
"""Accepted regular replay must remain recoverable through prior Redo disposal."""
import json,os,sys,traceback
from pathlib import Path
import FreeCAD as App,FreeCADGui as Gui,OpenMatrix9Gui as OM
from PySide6 import QtCore
out=Path(os.environ['OM9_SMOKE_OUTPUT']);report=dict(module=OM.__file__,checks=[],observations=[])
sys.path.insert(0,os.environ['OM9_REPLAY_RETIREMENT_PROBE']);import OM9ReplayRetirement as probe
report['probe']=probe.__file__
def state(doc):return dict(booked=doc.getBookedTransactionID(),pending=doc.HasPendingTransaction,undo=list(doc.UndoNames),redo=list(doc.RedoNames))
def check(name,value):report['checks'].append(dict(name=name,passed=bool(value)))
def run():
 try:
  Gui.activateWorkbench('OpenMatrix9Workbench')
  for action in ['value','close','remove','clear']:
   doc=App.newDocument('DiscardedRedo');doc.UndoMode=1
   child=doc.getObject(probe.create(doc.Name));doc.recompute();doc.clearUndos()
   doc.openTransaction('Prior redo');child.Value='prior-redo-value';doc.commitTransaction();doc.undo()
   doc.openTransaction('Caller');before=state(doc);value=child.Value
   result=probe.run(doc.Name,action,'discarded_redo');live=doc.Name in App.listDocuments()
   check(action+' actual old Redo destruction callback attempted',result['callbacks']==1)
   check(action+' old Redo callback mutation blocked',result['blocked']==1)
   check(action+' rejects and completes checked rollback cleanup',not result['accepted']and result['rollback']and result['complete']and 'StaleGeometry'in result['error'])
   check(action+' keeps native owner and child alive',live and doc.getObject('Child')is child)
   check(action+' restores value and clears paired output',child.Value==value and child.Output=='')
   check(action+' retains exact empty caller booking and original Redo',state(doc)==before)
   doc.abortTransaction();doc.redo()
   check(action+' original native Redo remains executable',child.Value=='prior-redo-value')
   report['observations'].append(dict(action=action,before=before,after=state(doc),result=result,value=child.Value,output=child.Output))
   App.closeDocument(doc.Name)
  report['ok']=all(c['passed']for c in report['checks'])
 except Exception:report['ok']=False;report['error']=traceback.format_exc()
 finally:
  (out/'results.json').write_text(json.dumps(report,indent=2))
  for name in list(App.listDocuments()):App.closeDocument(name)
  QtCore.QTimer.singleShot(100,Gui.getMainWindow().close)
QtCore.QTimer.singleShot(1000,run)
