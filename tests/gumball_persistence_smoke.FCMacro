"""Save genuine UI Gumball results and immutable facts for a separate process."""
import json, os, sys, traceback, tempfile
from pathlib import Path
import FreeCAD as App, FreeCADGui as Gui, Part
from PySide6 import QtCore, QtWidgets, QtTest
sys.path.insert(0,str(Path(__file__).parent))
from gumball_fixture import GumballUI, durable_facts
out=Path(os.environ['OM9_SMOKE_OUTPUT']);report={'checks':[],'feature_ids':['OM9-INFO-020']}
def check(name,value):
    report['checks'].append({'name':name,'passed':bool(value)})
    if not value:raise AssertionError(name)
def run():
    ui=None
    try:
        import OpenMatrix9Gui as native, ThreeDm
        report['module']=native.__file__
        Gui.activateWorkbench('OpenMatrix9Workbench');doc=App.newDocument('GumballPersistence');doc.UndoMode=1
        box=doc.addObject('Part::Feature','Box');box.Shape=Part.makeBox(2,3,4);box.Label='Gumball durable solid';doc.recompute()
        Gui.activeDocument().activeView().viewAxonometric();ui=GumballUI(native);ui.select(box);ui.command('Gumball On')
        for handle,value in [('RotateZ','90'),('ScaleX','2'),('MoveX','5.123456789123 mm')]:
            before=durable_facts(box);ui.numeric(handle,value);after=durable_facts(box)
            check(handle+' commits native geometry',before.get('geometry')!=after.get('geometry'))
            doc.undo();ui.settle();check(handle+' Undo restores exact geometry',durable_facts(box)['geometry']==before['geometry'])
            doc.redo();ui.settle();check(handle+' Redo restores exact geometry',durable_facts(box)['geometry']==after['geometry'])
        ui.command('Layer=1');ui.select(box)
        button=Gui.getMainWindow().findChild(QtWidgets.QToolButton,'OM9LayerArrow0');check('native current layer control exists',button is not None);button.click();ui.settle()
        layer=next(o for o in doc.Objects if getattr(o,'OM9LayerIndex',0)==1 and getattr(o,'OM9LayerSchema','')=='1')
        # This isolated host checkpoint's arrow selects the current layer.
        # Establish native source ownership before testing Gumball inheritance.
        # The copied output's membership and metadata remain Gumball's work.
        layer.addObject(box)
        box.addProperty('App::PropertyInteger','OM9OutputLayerIndex','OpenMatrix9')
        box.OM9OutputLayerIndex=1;doc.recompute();ui.select(box)
        check('source assigned to native layer',box in layer.Group and box.getTypeIdOfProperty('OM9OutputLayerIndex')=='App::PropertyInteger' and box.OM9OutputLayerIndex==1)
        before=set(o.Name for o in doc.Objects);ui.numeric('MoveY','7 mm',QtCore.Qt.AltModifier)
        copied=next(o for o in doc.Objects if o.Name not in before and o.TypeId=='Part::Feature')
        check('copy inherits native layer and material',copied in layer.Group and copied.OM9OutputLayerIndex==1 and durable_facts(copied)['color']==durable_facts(box)['color'] and bool(copied.OM9GumballIdentity))
        circle=doc.addObject('Part::Feature','Ellipse');circle.Shape=Part.Wire(Part.makeCircle(5));doc.recompute();ui.select(circle);ui.numeric('ScaleX','2')
        bounds=circle.Shape.optimalBoundingBox(False,False);report['ellipse_bounds']=[bounds.XLength,bounds.YLength]
        # OCCT optimal bounds include the native 1e-7 edge tolerance on each side.
        check('affine circle preserves native ellipse geometry',abs(bounds.XLength-20)<1e-6 and abs(bounds.YLength-10)<1e-6)
        group=doc.addObject('App::Part','PlacedGroup');member=doc.addObject('Part::Feature','Member');member.Shape=Part.makeBox(2,3,4);group.addObject(member);group.Placement.Base=App.Vector(30,0,0);doc.recompute()
        ui.select(group,member);ui.numeric('MoveX','5 mm');before=set(o.Name for o in doc.Objects);ui.numeric('MoveY','4 mm',QtCore.Qt.AltModifier)
        groupcopy=next(o for o in doc.Objects if o.Name not in before and o.TypeId=='App::Part')
        check('saved group copies private native membership',groupcopy.Group[0]!=member and groupcopy.Group[0] not in group.Group and abs(group.Placement.Base.x-35)<1e-8 and abs(groupcopy.Placement.Base.y-4)<1e-8)
        occurrence=doc.addObject('App::Link','Occurrence');occurrence.setLink(box);occurrence.LinkPlacement.Base=App.Vector(40,0,0);doc.recompute();ui.select(occurrence);ui.numeric('MoveX','3 mm');before=set(o.Name for o in doc.Objects);ui.numeric('MoveY','4 mm',QtCore.Qt.AltModifier)
        occurrencecopy=next(o for o in doc.Objects if o.Name not in before and o.TypeId=='App::Link')
        check('saved Link copies independent occurrence and shared definition',occurrencecopy.LinkedObject==box and occurrence.LinkedObject==box and abs(occurrence.LinkPlacement.Base.x-43)<1e-8 and abs(occurrencecopy.LinkPlacement.Base.y-4)<1e-8)
        face=doc.addObject('Part::Feature','HoledFace');face.Shape=Part.Face(Part.Wire(Part.makeCircle(5))).cut(Part.Face(Part.Wire(Part.makeCircle(2))));doc.recompute();ui.select(face)
        Gui.activeDocument().activeView().viewAxonometric();ui.settle()
        end=ui.drag('MoveZ');QtTest.QTest.keyPress(ui.viewport,QtCore.Qt.Key_Control);ui.command('-5 mm');ui.release(end,QtCore.Qt.ControlModifier);QtTest.QTest.keyRelease(ui.viewport,QtCore.Qt.Key_Control)
        extrusion=doc.getObject('GumballExtrusion');check('negative extrusion retains holes and orientation',extrusion is not None and extrusion.Shape.isValid() and abs(extrusion.Shape.Volume-105*3.141592653589793)<1e-7)
        source=out/'source.3dm';ThreeDm.export_file(str(source),[box],geometry_only=True)
        imported=ThreeDm.import_file(str(source),doc,mode='preserve')
        retained=next(o for o in imported if o.isDerivedFrom('Part::Feature') and o.ViewObject.Visibility)
        retained_before=durable_facts(retained);ui.select(retained);ui.numeric('MoveX','2 mm');retained_after=durable_facts(retained)
        check('retained BRep move keeps native volume and source UUID',abs(retained_after['geometry'][0]-retained_before['geometry'][0]-2)<1e-8 and retained_after['geometry'][6]==retained_before['geometry'][6] and retained_after['source_uuid']==retained_before['source_uuid'])
        before=set(o.Name for o in doc.Objects);ui.numeric('MoveX','3 mm',QtCore.Qt.AltModifier)
        retainedcopy=next(o for o in doc.Objects if o.Name not in before and o.isDerivedFrom('Part::Feature'))
        exported=out/'gumball-retained.3dm';ThreeDm.export_preserved(str(exported),[retained,retainedcopy])
        records=json.loads(native.inspect3dm(str(exported)))['records'];ids=[r['source_uuid'] for r in records]
        check('retained copies export distinct archive UUIDs',len(records)==2 and len(set(ids))==2 and retained.OM9SourceUUID in ids)
        nativeitems=json.loads(native.read3dm(str(exported),str(out)))['items'];exportfacts=[]
        for item in nativeitems:
            shape=Part.Shape();shape.read(item['brep']);b=shape.optimalBoundingBox(False,False);exportfacts.append([round(v,9) for v in (b.XMin,b.YMin,b.ZMin,shape.Volume)])
        report['export_geometry']=exportfacts;report['expected_export_geometry']=[retained_after['geometry'],durable_facts(retainedcopy)['geometry']]
        check('retained export contains moved and copied native geometry',sorted(v[0] for v in exportfacts)==sorted([retained_after['geometry'][0],durable_facts(retainedcopy)['geometry'][0]]))
        names=[box.Name,copied.Name,circle.Name,face.Name,extrusion.Name,retained.Name,retainedcopy.Name,layer.Name,group.Name,member.Name,groupcopy.Name,groupcopy.Group[0].Name,occurrence.Name,occurrencecopy.Name]
        expected={'objects':[durable_facts(doc.getObject(n)) for n in names],'retained':[retained.Name,retainedcopy.Name],'export_geometry':sorted(exportfacts),'archive_ids':sorted(ids)}
        doc.recompute();doc.saveAs(str(out/'gumball.FCStd'));(out/'expected.json').write_text(json.dumps(expected,indent=2))
        check('save leaves no active gesture',native.gumballState()['phase']==1);report['ok']=True
    except Exception:report.update(ok=False,error=traceback.format_exc())
    finally:
        if ui:report['transcript']=ui.transcript()
        for name in list(App.listDocuments()):App.closeDocument(name)
        (out/'results.json').write_text(json.dumps(report,indent=2));Gui.getMainWindow().close()
QtCore.QTimer.singleShot(1200,run)
