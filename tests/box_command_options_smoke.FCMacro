import os,sys,json
sys.path.insert(0,'H:/FreeCAD-src/Mod/OpenMatrix9/tests')
from command_options_fixture_support import *

def start():
    Gui.runCommand('OM9_SolidBoxCornertoCornerHeight');settle()
def run():
    doc=App.newDocument('BoxMatrixOptions');doc.UndoMode=1
    start()
    check('Matrix Box default first corner text',prompt()=='First corner of base ( Diagonal 3Point Vertical Center ): ')
    check('Box uses common feature schema',field().property('om9OptionFeatureId')=='OM9-SOLID-012')
    marks=field().extraSelections()
    character=QtGui.QTextCursor(field().document());character.setPosition(int(field().property('om9InputStart'))-len(prompt()));character.setPosition(character.position()+1,QtGui.QTextCursor.KeepAnchor)
    report['question_render']={'text':character.selectedText(),'font_weight':character.charFormat().fontWeight(),'input_start':field().property('om9InputStart'),'cursor':field().textCursor().position()}
    check('Matrix question is bold',character.charFormat().fontWeight()==QtGui.QFont.Bold and any(s.format.fontWeight()==QtGui.QFont.Bold and s.cursor.selectedText()=='First corner of base' for s in marks))
    check('only single shortcut characters are underlined',all(any(s.format.fontUnderline() and s.cursor.selectedText()==letter for s in marks) for letter in ('D','3','V','C')) and not any(s.format.fontUnderline() and len(s.cursor.selectedText())>1 for s in marks))
    check('menu invocation recorded once',field().toPlainText().count('Command: _Box')==1)
    history=field().findChild(QtWidgets.QPlainTextEdit,'OM9CommandHistoryPane')
    check('history and live CMD share Matrix green',history.palette().color(QtGui.QPalette.Base)==field().palette().color(QtGui.QPalette.Base))
    pixels=history.viewport().grab().toImage();dark=sum(1 for y in range(pixels.height()) for x in range(min(300,pixels.width())) if max(pixels.pixelColor(x,y).red(),pixels.pixelColor(x,y).green(),pixels.pixelColor(x,y).blue())<100)
    rectangle=history.cursorRect(QtGui.QTextCursor(history.document().lastBlock()));report['history_render']={'cursor_last_rect':[rectangle.x(),rectangle.y(),rectangle.width(),rectangle.height()],'scroll':[history.verticalScrollBar().value(),history.verticalScrollBar().maximum()],'blocks':history.document().blockCount(),'viewport_height':history.viewport().height()}
    report['history_text_pixels']=dark;check('history visibly renders actual invocation',dark>8)
    command('D');check('D selects mode without document geometry',len(doc.Objects)==0 and 'First corner of base' in prompt())
    command('0,0');check('Diagonal next phase only shows Cube',prompt()=='Other corner of box ( Cube ): ')
    click_option('Cube');check('Cube uses shared click routing',prompt()=='Other corner of box: ' and len(doc.Objects)==0)
    command('3,3,3');o=doc.Objects[-1]
    check('clicked Cube native volume',o.Shape.isValid() and abs(o.Shape.Volume-27)<1e-6 and 'Cube' in o.SolidParameters)
    doc.undo();check('one native Undo',len(doc.Objects)==0);doc.redo();check('native Redo',len(doc.Objects)==1)
    o.Visibility=False
    start();click_option('Diagonal');command('0,0');command('2,3');check('Diagonal height phase',prompt()=='Height. Press Enter to use width <3 mm>: ')
    command('4');o=doc.Objects[-1];check('clicked Diagonal native geometry',abs(o.Shape.Volume-24)<1e-6 and 'Diagonal' in o.SolidParameters)
    start();command('C');command('0,0');command('2');check('Width uses actual Length default',prompt()=='Width. Press Enter to use length <2 mm>: ')
    command();check('Height uses actual Width default',prompt()=='Height. Press Enter to use width <2 mm>: ')
    command();check('numeric phase Enter commits original native geometry',abs(doc.Objects[-1].Shape.Volume-8)<1e-6)
    start();command('bad-point');check('invalid geometric draft retained',draft()=='bad-point' and len(doc.Objects)==3)
    click_option('Diagonal');check('nonempty draft prevents option click',draft()=='bad-point' and len(doc.Objects)==3)
    key(QtCore.Qt.Key_Escape);check('Esc cancels native command and draft',draft()=='' and len(doc.Objects)==3)
    command('_Box');check('typed Box invocation already recorded once',field().toPlainText().count('Command: _Box')==5)
    command('d');command('0,0');command('2,3');command('4');check('lowercase mnemonic same native geometry',abs(doc.Objects[-1].Shape.Volume-24)<1e-6)
    report['source_sha256']['rust/src/solid.rs']=hashlib.sha256((Path('H:/FreeCAD-src/Mod/OpenMatrix9')/'rust/src/solid.rs').read_bytes()).hexdigest()
    start();field().grab().save(str(out/'matrix-box-prompt.png'));Gui.getMainWindow().grab().save(str(out/'matrix-box-native.png'))
    key(QtCore.Qt.Key_Escape)

QtCore.QTimer.singleShot(1800,lambda:execute(run))
