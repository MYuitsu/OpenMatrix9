# SPDX-License-Identifier: LGPL-2.1-or-later
"""Isolated native lifetime witness: closing the replay owner from a result observer."""
import json,os,traceback
from pathlib import Path
import FreeCAD as App,FreeCADGui as Gui,Part,OpenMatrix9Gui as OM
from PySide6 import QtCore,QtGui,QtWidgets
out=Path(os.environ['OM9_SMOKE_OUTPUT'])
report=dict(module=OM.__file__,checks=[],phase='starting',callbacks=0)
def save():
 (out/'results.json').write_text(json.dumps(report,indent=2),encoding='utf-8')
def check(name,value):report['checks'].append(dict(name=name,passed=bool(value)))
def settle():
 loop=QtCore.QEventLoop();QtCore.QTimer.singleShot(80,loop.quit);loop.exec()
def enter(console,text):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier))
class Observer:
 def __init__(self,name):self.name=name;self.calls=0
 def slotChangedObject(self,obj,prop):
  if self.calls or prop!='OM9GeometryResult':return
  if not obj.Document or obj.Document.Name!=self.name or obj.Name!='Circle' or not obj.OM9GeometryResult:return
  self.calls+=1;report['callbacks']=self.calls;report['phase']='before_close';save()
  App.closeDocument(self.name)
  report['phase']='after_close';report['document_alive_after_callback']=self.name in App.listDocuments();save()
def run():
 observer=None
 try:
  Gui.activateWorkbench('OpenMatrix9Workbench');settle()
  console=Gui.getMainWindow().findChild(QtWidgets.QPlainTextEdit,'OM9CommandTranscript')
  doc=App.newDocument('CircleHistoryCloseCallback');name=doc.Name;doc.UndoMode=1
  OM.setUnitContext(name,1.,1.,.01,.001,.01)
  settings=doc.addObject('OpenMatrix9Gui::HistorySettings','OM9HistorySettings');settings.BrokenHistoryWarning=False
  source=doc.addObject('Part::Feature','Source');source.Shape=Part.Vertex(App.Vector(3,4,5));doc.recompute()
  for text in ['Circle','History=Yes','Point=Source.Vertex1','Radius=2']:enter(console,text)
  settle();child=doc.getObject('Circle');check('recorded Circle exists before lifetime probe',child is not None and child.Recorded and bool(child.OM9GeometryResult))
  source.Shape=Part.Vertex(App.Vector(6,8,10));observer=Observer(name);App.addDocumentObserver(observer)
  report['phase']='before_recompute';save();child.touch();doc.recompute()
  App.removeDocumentObserver(observer);observer=None
  alive=name in App.listDocuments();check('result callback executes once',report['callbacks']==1)
  check('replay owner survives observer close attempt',alive)
  if alive:
   child=App.getDocument(name).getObject('Circle')
   check('rejected close attempt invalidates paired output',child.Shape.isNull() and not child.OM9GeometryResult and 'StaleGeometry'in child.getStatusString())
  report['phase']='recompute_returned';report['ok']=all(c['passed']for c in report['checks'])
 except Exception:report['ok']=False;report['error']=traceback.format_exc()
 finally:
  if observer:App.removeDocumentObserver(observer)
  for name in list(App.listDocuments()):App.closeDocument(name)
  save();QtCore.QTimer.singleShot(100,Gui.getMainWindow().close)
QtCore.QTimer.singleShot(1200,run)
