"""RCORE-01: real native Edit outputs own operation/source evidence after deletion."""
import json,os,traceback
from pathlib import Path
import FreeCAD as App,FreeCADGui as Gui,Part,OpenMatrix9Gui as OM
from PySide6 import QtCore,QtGui,QtWidgets
out=Path(os.environ['OM9_SMOKE_OUTPUT']);report={'module':OM.__file__,'checks':[]}
def check(name,value):report['checks'].append(dict(name=name,passed=bool(value)))
def events():QtWidgets.QApplication.processEvents()
def enter(text=''):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier));events()
def source(d,n,s):
 o=d.addObject('Part::Feature',n);o.Shape=s;o.Label='Evidence '+n;return o
def start(command,objects):
 Gui.Selection.clearSelection()
 for o in objects:Gui.Selection.addSelection(o)
 enter(command);enter()
def accept():
 dialog=next(d for d in Gui.getMainWindow().findChildren(QtWidgets.QDialog,'OM9EditOptions') if d.isVisible())
 button=dialog.findChild(QtWidgets.QDialogButtonBox).button(QtWidgets.QDialogButtonBox.Ok)
 if not button.isEnabled():raise AssertionError(dialog.findChild(QtWidgets.QLabel,'OM9EditStatus').text())
 button.click();events()
def bounds(s):b=s.BoundBox;return [b.XMin,b.XMax,b.YMin,b.YMax,b.ZMin,b.ZMax]
def close(a,b):return len(a)==len(b) and all(abs(x-y)<1e-6 for x,y in zip(a,b))
def inspect(d,command,fid,names,expected_total,metric,expected_count,kind):
 objects=[o for o in d.Objects if getattr(o,'OM9FeatureId','')==fid]
 check(command+' native result geometry',len(objects)==expected_count and abs(sum(getattr(o.Shape,metric) for o in objects)-expected_total)<1e-6)
 saved={}
 for index,o in enumerate(objects):
  label=command+' output '+str(index)
  raw=getattr(o,'OM9GeometryResult','');saved[o.Name]=raw
  try:value=json.loads(raw)
  except (ValueError,TypeError):value={}
  expected_operation='Boolean' if kind>=4 else 'NativeEdit'
  check(label+' accepted actual operation',value.get('schema_version')==1 and value.get('status')=='accepted' and value.get('operation')==expected_operation)
  ctx=value.get('operation_context',{}) or {};snapshots=value.get('input_snapshots',[])
  check(label+' actual feature/options/output identity',ctx.get('feature_id')==fid and ctx.get('kind')==kind and ctx.get('output_index')==index and ctx.get('output_count')==expected_count and value.get('input_identity',{}).get('name')==o.Name)
  check(label+' complete owned source evidence',len(snapshots)==len(names) and [s.get('source_attributes',{}).get('object_name') for s in snapshots]==names and all(s.get('source_attributes',{}).get('label')=='Evidence '+n for s,n in zip(snapshots,names)))
  check(label+' honest conversion and lifetime',value.get('lifetime')=='immutable_native_operation_evidence_not_current_validity' and value.get('topology_map','missing') is None and value.get('conversion_reports',[{}])[0].get('phase')=='native_edit_construction' and 'upstream_archive_conversion' not in raw)
  master=None
  if value.get('output_snapshots'):
   master=Part.Shape();master.importBrepFromString(value['output_snapshots'][0]['geometry_data']['native_master']['payload'])
  check(label+' native master equals published shape',master is not None and master.isValid() and close(bounds(master),bounds(o.Shape)) and abs(getattr(master,metric)-getattr(o.Shape,metric))<1e-6)
  check(label+' output result is read only',bool(raw) and 'ReadOnly' in o.getPropertyStatus('OM9GeometryResult'))
 d.undo();check(command+' atomic Undo removes paired outputs',not any(getattr(o,'OM9FeatureId','')==fid for o in d.Objects) and all(d.getObject(n) is not None for n in names))
 d.redo();check(command+' Redo retains exact paired evidence',all(getattr(d.getObject(n),'OM9GeometryResult','')==raw for n,raw in saved.items()))
 for n,raw in saved.items():
  if not raw:continue
  master=Part.Shape();master.importBrepFromString(json.loads(raw)['output_snapshots'][0]['geometry_data']['native_master']['payload']);check(command+' Redo Shape/master pairing '+n,close(bounds(master),bounds(d.getObject(n).Shape)) and abs(getattr(master,metric)-getattr(d.getObject(n).Shape,metric))<1e-6)
 path=out/(command+'.FCStd');d.recompute();d.saveAs(str(path));App.closeDocument(d.Name);d=App.openDocument(str(path))
 check(command+' FCStd retains exact paired evidence',all(getattr(d.getObject(n),'OM9GeometryResult','')==raw for n,raw in saved.items()))
 for n,raw in saved.items():
  if not raw:continue
  master=Part.Shape();master.importBrepFromString(json.loads(raw)['output_snapshots'][0]['geometry_data']['native_master']['payload']);check(command+' FCStd Shape/master pairing '+n,close(bounds(master),bounds(d.getObject(n).Shape)) and abs(getattr(master,metric)-getattr(d.getObject(n).Shape,metric))<1e-6)
 App.closeDocument(d.Name)
def run():
 global console
 try:
  Gui.activateWorkbench('OpenMatrix9Workbench');events();console=Gui.getMainWindow().findChild(QtWidgets.QPlainTextEdit,'OM9CommandTranscript')
  d=App.newDocument('EditResultJoin');d.UndoMode=1
  source(d,'Join',Part.makeLine(App.Vector(80,0,0),App.Vector(81,0,0)))
  a=source(d,'A',Part.makeLine(App.Vector(0,0,0),App.Vector(5,0,0)));b=source(d,'B',Part.makeLine(App.Vector(10,0,0),App.Vector(5,0,0)));d.recompute()
  start('Join',[a,b]);accept();inspect(d,'Join','OM9-TOP11-008',['A','B'],10,'Length',1,1)
  d=App.newDocument('EditResultExplode');d.UndoMode=1;group=d.addObject('App::Part','Group');group.Placement.Base=App.Vector(100,20,9)
  a=source(d,'Wire',Part.makePolygon([App.Vector(0,0,0),App.Vector(4,0,0),App.Vector(4,3,0)]));group.addObject(a);a.Placement.Base=App.Vector(7,-4,2);d.recompute()
  start('Explode',[a]);accept()
  for o in [o for o in d.Objects if getattr(o,'OM9FeatureId','')=='OM9-TOP11-005']:
   parent=o.getGlobalPlacement()*o.Placement.inverse();world=o.Shape.copy();world.transformShape(parent.toMatrix());check('Explode source world once '+o.Name,close(bounds(world),[107,111,16,16,11,11]) or close(bounds(world),[111,111,16,19,11,11]))
  inspect(d,'Explode','OM9-TOP11-005',['Wire'],7,'Length',2,2)
  for command,fid,total,kind in [('BooleanDifference','OM9-SOLID-001',500,4),('BooleanIntersection','OM9-SOLID-002',500,5),('BooleanUnion','OM9-SOLID-003',1500,6),('Boolean2Objects','OM9-SOLID-004',1500,7)]:
   d=App.newDocument('EditResult'+command);d.UndoMode=1;a=source(d,'A',Part.makeBox(10,10,10));b=source(d,'B',Part.makeBox(10,10,10,App.Vector(5,0,0)));d.recompute()
   start(command,[a,b] if kind>=6 else [a])
   if kind<6:enter('B');enter()
   accept();inspect(d,command,fid,['A','B'],total,'Volume',1,kind)
  d=App.newDocument('EditResultTrim');d.UndoMode=1;a=source(d,'A',Part.makeLine(App.Vector(-5,0,0),App.Vector(5,0,0)));b=source(d,'B',Part.makeLine(App.Vector(0,-5,0),App.Vector(0,5,0)));d.recompute()
  start('Trim',[a,b]);enter('A@3,0,0');enter();inspect(d,'Trim','OM9-TOP11-010',['A','B'],15,'Length',3,3)
  report['ok']=all(c['passed'] for c in report['checks'])
 except Exception:report['ok']=False;report['error']=traceback.format_exc()
 finally:
  for n in list(App.listDocuments()):App.closeDocument(n)
  (out/'results.json').write_text(json.dumps(report,indent=2),encoding='utf-8');QtCore.QTimer.singleShot(100,Gui.getMainWindow().close)
QtCore.QTimer.singleShot(1200,run)
