# SPDX-License-Identifier: LGPL-2.1-or-later
# OM9-CURVE-006: actual native geometry, menu/mouse, transaction and layer checks.
import json, math, os, sys, traceback
from pathlib import Path
import FreeCAD as App, FreeCADGui as Gui, Part
from PySide6 import QtCore, QtGui, QtWidgets, QtTest
sys.path.insert(0,os.environ['OM9_TEST_NATIVE_DIR'])
sys.path.insert(0,str(Path(__file__).parent))
from command_console_support import command_input, command_prompt
out=Path(os.environ['OM9_SMOKE_OUTPUT']);out.mkdir(parents=True,exist_ok=True)
result={'checks':[]}
def check(name,ok):
    result['checks'].append({'name':name,'passed':bool(ok)})
    (out/'progress.json').write_text(json.dumps(result,indent=2),encoding='utf-8')
    if not ok:raise AssertionError(name)
def settle():
    loop=QtCore.QEventLoop();QtCore.QTimer.singleShot(180,loop.quit);loop.exec()
def enter(text):
    result['last_input']=text
    (out/'progress.json').write_text(json.dumps(result,indent=2),encoding='utf-8')
    field.setFocus();field.setText(text);QtTest.QTest.keyClick(field,QtCore.Qt.Key_Return);settle()
def outputs(document,role='Ellipse'):
    return [o for o in document.Objects if 'OM9FeatureId' in o.PropertiesList and o.OM9FeatureId=='OM9-CURVE-006' and o.OM9Role==role]
def ellipse(*inputs,menu=False):
    old={o.Name for o in outputs(doc)}
    if menu:window.findChild(QtGui.QAction,'Ellipse').trigger();settle()
    else:enter('Ellipse')
    for text in inputs:enter(text)
    new=[o for o in outputs(doc) if o.Name not in old]
    check('One ellipse output '+str(inputs),len(new)==1)
    return new[0]
def exact(o,a,b,c,n=(0,0,1),direction=None):
    edge=o.Shape.Edges[0];curve=edge.Curve
    return o.Shape.isValid() and o.Shape.isClosed() and len(o.Shape.Edges)==1 and isinstance(curve,Part.Ellipse) and abs(curve.MajorRadius-a)<1e-6 and abs(curve.MinorRadius-b)<1e-6 and (curve.Center-App.Vector(*c)).Length<1e-6 and abs(curve.Axis.dot(App.Vector(*n)))>0.999999 and (direction is None or abs(curve.XAxis.dot(App.Vector(*direction)))>0.999999)
def feature(name,shape):
    o=doc.addObject('Part::Feature',name);o.Shape=shape;doc.recompute();return o
def screen(point):
    viewer=next(w for w in window.findChild(QtWidgets.QMdiArea).activeSubWindow().findChildren(QtWidgets.QWidget) if w.metaObject().className()=='Gui::View3DInventorViewer' and w.isVisible())
    target=viewer.viewport();p=view.getPointOnScreen(App.Vector(*point));return target,QtCore.QPoint(int(p[0]),target.height()-int(p[1]))
def run():
    global doc,window,field,view
    try:
        Gui.activateWorkbench('OpenMatrix9Workbench');import OpenMatrix9Gui
        result['native_module']=OpenMatrix9Gui.__file__
        check('New isolated native module loaded',Path(OpenMatrix9Gui.__file__).parent.resolve()==Path(os.environ['OM9_TEST_NATIVE_DIR']).resolve())
        window=Gui.getMainWindow();window.resize(1400,950);field=command_input(window)
        action=window.findChild(QtGui.QAction,'Ellipse');check('Ellipse action exists',action is not None)
        doc=App.newDocument('EllipseNative');doc.UndoMode=1;view=Gui.activeDocument().activeView();view.viewTop();settle()
        check('Editable document enables Ellipse',action.isEnabled())
        o=ellipse('1,2,3','6,2,3','1,5,3',menu=True);name=o.Name
        check('Center exact native ellipse',exact(o,5,3,(1,2,3),direction=(1,0,0)))
        check('Root output snapshot metadata',o.TypeId=='Part::Feature' and not o.InList and not o.EllipseDeformable and o.EllipseApproxDeviation.Value==0)
        doc.undo();settle();check('Single Undo removes ellipse',doc.getObject(name) is None)
        doc.redo();settle();check('Redo restores exact ellipse',exact(doc.getObject(name),5,3,(1,2,3)))
        o=ellipse('0,0','3,0','0,5');check('Short first axis canonicalizes major direction',exact(o,5,3,(0,0,0),direction=(0,1,0)))
        o=ellipse('Diameter','1,2,3','11,2,8','6,5,12');check('Diameter projects endpoint and center in CPlane',exact(o,5,3,(6,2,3)))
        o=ellipse('Diameter','0,0','1cm','3mm');check('Diameter numeric full length and explicit units',exact(o,5,3,(5,0,0)))
        o=ellipse('Corner','-5,-3,4','5,3,10');check('Corner uses enclosing CPlane rectangle',exact(o,5,3,(0,0,4)))
        o=ellipse('Vertical','0,0,2','3,4,2','0,0,5');check('Vertical perpendicular construction plane',exact(o,5,3,(0,0,2),n=(.8,-.6,0),direction=(.6,.8,0)))
        o=ellipse('FromFoci','1,2,-1','1,2,7','1,5,3');check('Spatial FromFoci exact analytic shape',exact(o,5,3,(1,2,3),n=(1,0,0),direction=(0,0,1)))
        o=ellipse('0,0','4','4');check('Equal semiaxes produce exact native circle',isinstance(o.Shape.Edges[0].Curve,Part.Circle) and abs(o.Shape.Edges[0].Curve.Radius-4)<1e-8)
        for degree,count in [(1,8),(2,9),(3,8),(5,12)]:
            o=ellipse('Deformable=Yes','PointCount='+str(count),'Degree='+str(degree),'0,0,7','5,0,7','0,3,7');c=o.Shape.Edges[0].Curve
            check('Deformable native degree/poles '+str(degree),isinstance(c,Part.BSplineCurve) and c.Degree==degree and c.NbPoles==count and c.isPeriodic() and o.Shape.isClosed() and o.Shape.isValid())
            check('Deformable finite approximation and plane '+str(degree),o.EllipseDeformable and math.isfinite(o.EllipseApproxDeviation.Value) and o.EllipseApproxDeviation.Value>0 and all(abs(p.z-7)<1e-6 for p in c.getPoles()))
            measured=max((c.value(c.FirstParameter+(c.LastParameter-c.FirstParameter)*i/1024)-App.Vector(5*math.cos(2*math.pi*i/1024),3*math.sin(2*math.pi*i/1024),7)).Length for i in range(1024))
            check('Native spline agrees with Rust sampled approximation '+str(degree),abs(measured-o.EllipseApproxDeviation.Value)<1e-6)
        count=len(doc.Objects);undo=doc.UndoCount;enter('Ellipse');enter('0,0');enter('5,0')
        for text in ['2,0','Degree=99','Deformable=Maybe','History=Yes']:
            enter(text);check('Rejected input preserves session/document '+text,len(doc.Objects)==count and doc.UndoCount==undo and command_prompt(window).text()!='Command: ')
        enter('Undo');enter('8,0');enter('0,4');check('Undo recovers rejected last axis',len(doc.Objects)==count+1 and exact(outputs(doc)[-1],8,4,(0,0,0)))
        count=len(doc.Objects);enter('Ellipse');enter('FromFoci');enter('-4,0');enter('4,0');enter('0,0');check('Infeasible foci do not create partial geometry',len(doc.Objects)==count);enter('0,3');check('Foci failure recovers',len(doc.Objects)==count+1)
        count=len(doc.Objects);enter('Ellipse');enter('0,0');enter('5,0');enter('Cancel');check('Cancel creates no objects',len(doc.Objects)==count)
        path=feature('SpatialPath',Part.makeLine(App.Vector(1,2,3),App.Vector(11,2,3)))
        o=ellipse('AroundCurve','Curve=SpatialPath.Edge1','OnCurve=0.25','3.5,7,3','3.5,2,6');check('AroundCurve center and local tangent normal',exact(o,5,3,(3.5,2,3),n=(1,0,0),direction=(0,1,0)))
        count=len(doc.Objects);enter('Ellipse');enter('AroundCurve');enter('Curve=SpatialPath.Edge1');enter('OnCurve=2');check('Around invalid fraction is recoverable',len(doc.Objects)==count and '0..1' in command_prompt(window).text());enter('OnCurve=0.5');enter('Undo');enter('OnCurve=0.75');enter('5');enter('3');check('Around center Undo keeps selected path',len(doc.Objects)==count+1 and exact(outputs(doc)[-1],5,3,(8.5,2,3),n=(1,0,0)))
        count=len(doc.Objects);enter('Ellipse');enter('AroundCurve');enter('Curve=SpatialPath.Edge1');path.Placement.Base=App.Vector(2,0,0);doc.recompute();enter('OnCurve=0.5');check('Changed reference rejected before center',len(doc.Objects)==count and ('changed' in command_prompt(window).text().lower() or 'stale' in command_prompt(window).text().lower()));enter('Undo');enter('Curve=SpatialPath.Edge1');enter('OnCurve=0.5');enter('5');enter('3');check('Stale reference Undo and reselect recovers',len(doc.Objects)==count+1 and exact(outputs(doc)[-1],5,3,(8,2,3),n=(1,0,0)))
        # Active layer membership/style and all three MarkFoci outputs are atomic.
        enter('Layer=Metal 02');g=next(o for o in doc.Objects if 'OM9LayerSchema' in o.PropertiesList and o.OM9LayerIndex==2)
        previous={o.Name for o in doc.Objects};undo=doc.UndoCount
        o=ellipse('FromFoci','MarkFoci=Yes','-4,0','4,0','0,3');made=[x for x in doc.Objects if x.Name not in previous];names=[x.Name for x in made]
        check('MarkFoci exactly ellipse and two separate point objects',len(made)==3 and sorted(x.OM9Role for x in made)==['Ellipse','Focus1','Focus2'])
        focus=[x for x in made if x.OM9Role!='Ellipse'];check('MarkFoci exact input focus positions',sorted((x.Shape.Vertexes[0].Point.x,x.Shape.Vertexes[0].Point.y,x.Shape.Vertexes[0].Point.z) for x in focus)==[(-4.,0.,0.),(4.,0.,0.)])
        check('Ellipse and foci current layer membership',all(x in g.Group and x.OM9OutputLayerIndex==2 for x in made))
        check('Layer ellipse and focus colors',tuple(o.ViewObject.LineColor)[:3]==tuple(g.OM9LayerColor)[:3] and all(tuple(x.ViewObject.PointColor)[:3]==tuple(g.OM9LayerColor)[:3] for x in focus))
        check('MarkFoci one Undo transaction',doc.UndoCount==undo+1);doc.undo();settle();check('Single Undo removes all three outputs',all(doc.getObject(n) is None for n in names));doc.redo();settle();check('Redo restores all three layer members',all(doc.getObject(n) in g.Group for n in names))
        old_color=tuple(g.OM9LayerColor);chosen=QtGui.QColor(12,100,180);dialog_accepted={'yes':False}
        def accept_color():
            dialog=next((w for w in QtWidgets.QApplication.topLevelWidgets() if isinstance(w,QtWidgets.QColorDialog)),None)
            if dialog is None:QtCore.QTimer.singleShot(100,accept_color)
            else:dialog.setCurrentColor(chosen);dialog.accept();dialog_accepted['yes']=True
        QtCore.QTimer.singleShot(100,accept_color)
        dock=window.findChild(QtWidgets.QDockWidget,'OpenMatrix9Sidebar');dock.findChild(QtWidgets.QToolButton,'OM9LayerSwatch1').click();settle()
        def all_layer_colors(color):
            return all(all(abs(a-b)<1e-6 for a,b in zip(tuple(doc.getObject(n).ViewObject.PointColor if doc.getObject(n).OM9Role!='Ellipse' else doc.getObject(n).ViewObject.LineColor)[:3],color[:3])) for n in names)
        check('Layer swatch recolors ellipse and both focus markers',dialog_accepted['yes'] and all_layer_colors(tuple(g.OM9LayerColor)))
        doc.undo();settle();check('Layer color Undo restores ellipse and focus marker colors',all_layer_colors(old_color));doc.redo();settle();check('Layer color Redo restores all output colors',all_layer_colors(tuple(g.OM9LayerColor)))
        dock=window.findChild(QtWidgets.QDockWidget,'OpenMatrix9Sidebar');lock_button=dock.findChild(QtWidgets.QToolButton,'OM9LayerLock1');lock_button.click();settle();locked_count=len(doc.Objects);locked_undo=doc.UndoCount
        ellipse_inputs=['Ellipse','FromFoci','MarkFoci=Yes','-4,0','4,0','0,3']
        for text in ellipse_inputs:enter(text)
        check('Locked layer rejects ellipse and foci atomically',len(doc.Objects)==locked_count and doc.UndoCount==locked_undo and 'locked' in command_prompt(window).text().lower());enter('Cancel');lock_button.click();settle()
        dock=window.findChild(QtWidgets.QDockWidget,'OpenMatrix9Sidebar');dock.findChild(QtWidgets.QToolButton,'OM9Group5').click();settle()
        button=next(b for b in dock.findChildren(QtWidgets.QToolButton) if b.property('om9IconKey')=='CurveEllipseFromCenter');check('Ellipse sidebar enabled',button.isEnabled())
        QtTest.QTest.mouseClick(button,QtCore.Qt.RightButton);settle();check('Ellipse right-click Diameter prompt','First axis start' in command_prompt(window).text());enter('-5,0');enter('5,0');enter('0,3');check('Right-click Diameter commits analytic ellipse',exact(outputs(doc)[-1],5,3,(0,0,0)))
        enter('Osnap Off');view.viewTop();view.fitAll();settle();dock=window.findChild(QtWidgets.QDockWidget,'OpenMatrix9Sidebar');button=next(b for b in dock.findChildren(QtWidgets.QToolButton) if b.property('om9IconKey')=='CurveEllipseFromCenter');button.click();settle()
        viewer=next(w for w in window.findChild(QtWidgets.QMdiArea).activeSubWindow().findChildren(QtWidgets.QWidget) if w.metaObject().className()=='Gui::View3DInventorViewer' and w.isVisible());target=viewer.viewport();center=target.rect().center();first=center+QtCore.QPoint(75,-25);second=center+QtCore.QPoint(-15,-55)
        count=len(doc.Objects);QtTest.QTest.mouseClick(target,QtCore.Qt.LeftButton,pos=center);settle();QtTest.QTest.mouseClick(target,QtCore.Qt.LeftButton,pos=first);settle()
        motion=QtGui.QMouseEvent(QtCore.QEvent.MouseMove,QtCore.QPointF(second),QtCore.QPointF(target.mapToGlobal(second)),QtCore.Qt.NoButton,QtCore.Qt.NoButton,QtCore.Qt.ShiftModifier);QtWidgets.QApplication.sendEvent(target,motion);settle()
        from pivy import coin
        search=coin.SoSearchAction();search.setSearchingAll(True);search.setName('OM9CurvePreviewLine');search.apply(view.getSceneGraph());preview=search.getPath()
        check('Mouse hover closed ellipse preview without objects',preview is not None and preview.getTail().point.getNum()==129 and len(doc.Objects)==count)
        QtTest.QTest.mouseClick(target,QtCore.Qt.LeftButton,QtCore.Qt.ShiftModifier,pos=second);settle();check('Mouse axes commit exact closed ellipse',len(doc.Objects)==count+1 and isinstance(outputs(doc)[-1].Shape.Edges[0].Curve,Part.Ellipse) and outputs(doc)[-1].Shape.isClosed());search.apply(view.getSceneGraph());check('Commit clears transient preview',search.getPath() is None)
        # Native edge and center picks on a bounded elevated path.
        mousepath=feature('MousePath',Part.makeLine(App.Vector(30,35,5),App.Vector(40,35,5)));view.fitAll();settle();enter('Ellipse');enter('AroundCurve');target,pos=screen((35,35,5));QtTest.QTest.mouseClick(target,QtCore.Qt.LeftButton,pos=pos);settle();check('Mouse selects native AroundCurve edge','OnCurve' in command_prompt(window).text());QtTest.QTest.mouseClick(target,QtCore.Qt.LeftButton,pos=pos);settle();enter('5');enter('3');c=outputs(doc)[-1].Shape.Edges[0].Curve;check('Mouse center stays on exact elevated edge',abs(c.Center.y-35)<1e-6 and abs(c.Center.z-5)<1e-6 and abs(c.Axis.x)>0.999999)
        count=len(doc.Objects);enter('Ellipse');enter('0,0');other=App.newDocument('EllipseOther');settle();enter('5');check('Document switch cancels Ellipse',len(doc.Objects)==count and not other.Objects);App.closeDocument(other.Name);Gui.setActiveDocument(doc.Name);settle()
        group_name=g.Name;saved={o.Name:(o.OM9Role,o.Shape.copy()) for o in doc.Objects if 'OM9FeatureId' in o.PropertiesList and o.OM9FeatureId=='OM9-CURVE-006'};file=out/'ellipses.FCStd';doc.saveAs(str(file));App.closeDocument(doc.Name);doc=App.openDocument(str(file));settle()
        check('FCStd restores ellipse/foci identities and geometry',all(doc.getObject(n) is not None and doc.getObject(n).OM9Role==role and doc.getObject(n).Shape.isValid() and abs(doc.getObject(n).Shape.Length-shape.Length)<1e-6 for n,(role,shape) in saved.items()))
        group=doc.getObject(group_name);check('FCStd restores layer membership',all(doc.getObject(n) in group.Group for n in names))
        window.grab().save(str(out/'ellipse-runtime.png'));result['ok']=True
    except Exception:
        result['ok']=False;result['error']=traceback.format_exc();result['prompt']=command_prompt(window).text() if 'window' in globals() else ''
    finally:
        (out/'results.json').write_text(json.dumps(result,indent=2),encoding='utf-8')
        for name in list(App.listDocuments()):
            if name.startswith('Ellipse'):App.closeDocument(name)
        QtCore.QTimer.singleShot(0,QtWidgets.QApplication.quit)
QtCore.QTimer.singleShot(1800,run)
