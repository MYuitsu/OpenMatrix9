"""RCORE-01: repeated source evidence must not allocate an unbounded output batch."""
import os,json,traceback
from pathlib import Path
import FreeCAD as App,FreeCADGui as Gui,Part,OpenMatrix9Gui as OM
from PySide6 import QtCore,QtGui,QtWidgets
out=Path(os.environ['OM9_SMOKE_OUTPUT']);report={'module':OM.__file__,'checks':[]}
def check(name,value):report['checks'].append(dict(name=name,passed=bool(value)))
def events():QtWidgets.QApplication.processEvents()
def enter(text=''):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier));events()
def run():
 global console
 try:
  Gui.activateWorkbench('OpenMatrix9Workbench');events();console=Gui.getMainWindow().findChild(QtWidgets.QPlainTextEdit,'OM9CommandTranscript')
  d=App.newDocument('EditResultBatchBudget');d.UndoMode=1;a=d.addObject('Part::Feature','Faces')
  a.Shape=Part.makeCompound([Part.makePlane(1,1,App.Vector(3*i,0,0)) for i in range(64)]);d.recompute()
  check('source has 64 valid separable native faces',a.Shape.isValid() and len(a.Shape.Faces)==64 and abs(a.Shape.Area-64)<1e-6)
  d.openTransaction('Redo witness');a.Label='Redo witness';d.commitTransaction();d.undo();d.recompute()
  baseline=(tuple(o.Name for o in d.Objects),d.UndoCount,d.RedoCount,a.Shape.exportBrepToString())
  Gui.Selection.clearSelection();Gui.Selection.addSelection(a);enter('Explode');enter();enter()
  outputs=[o for o in d.Objects if getattr(o,'OM9FeatureId','')=='OM9-TOP11-005'];report['produced_result_bytes']=sum(len(getattr(o,'OM9GeometryResult','').encode('utf-8')) for o in outputs);report['produced_outputs']=len(outputs)
  check('aggregate result budget rejects the entire output batch',not outputs and 'budget' in console.toPlainText().lower())
  current=None
  if d.getObject('Faces'):current=(tuple(o.Name for o in d.Objects),d.UndoCount,d.RedoCount,d.getObject('Faces').Shape.exportBrepToString())
  check('aggregate budget rejection keeps source and Undo/Redo',current==baseline)
  enter('Cancel');d.redo();check('aggregate budget rejection keeps executable Redo',d.getObject('Faces') is not None and d.getObject('Faces').Label=='Redo witness')
  report['ok']=all(c['passed'] for c in report['checks'])
 except Exception:report['ok']=False;report['error']=traceback.format_exc()
 finally:
  for n in list(App.listDocuments()):App.closeDocument(n)
  (out/'results.json').write_text(json.dumps(report,indent=2),encoding='utf-8');QtCore.QTimer.singleShot(100,Gui.getMainWindow().close)
QtCore.QTimer.singleShot(1200,run)
