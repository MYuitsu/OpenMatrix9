"""Owned canonical group/member/subelement definitions without native baking."""
import json,math,os,sys,traceback
from pathlib import Path
import FreeCAD as App,FreeCADGui as Gui,Part
from PySide6 import QtCore
sys.path.insert(0,os.environ['OM9_TEST_NATIVE_DIR'])
out=Path(os.environ['OM9_SMOKE_OUTPUT']);out.mkdir(parents=True,exist_ok=True)
report={'checks':[],'descriptors':{}}
def check(name,value):
    report['checks'].append({'name':name,'passed':bool(value)})
    if not value:raise AssertionError(name)
def place(x,y,z,a=0):return App.Placement(App.Vector(x,y,z),App.Rotation(App.Vector(1,2,3),a))
def transformed(m,p):return App.Vector(*[sum(m[r][c]*[p.x,p.y,p.z][c] for c in range(3))+m[r][3] for r in range(3)])
def owned_point(row,t):
    d=row['geometry_data'];p=d['poles_xyz'];w=d['weights'] or [1]*len(p);n=d['degree']
    b=[math.comb(n,i)*t**i*(1-t)**(n-i)*w[i] for i in range(n+1)]
    return transformed(row['local_to_world'],App.Vector(*[sum(p[i][c]*b[i] for i in range(n+1))/sum(b) for c in range(3)]))
def native_state(doc):
    return {'objects':[o.Name for o in doc.Objects],'history':[doc.UndoCount,doc.RedoCount],
            'shapes':{o.Name:o.Shape.exportBrepToString() for o in doc.Objects if o.isDerivedFrom('Part::Feature')},
            'groups':{o.Name:[m.Name for m in o.Group] for o in doc.Objects if 'Group' in o.PropertiesList},
            'placements':{o.Name:list(o.Placement.toMatrix().A) for o in doc.Objects if 'Placement' in o.PropertiesList}}
def leaves(row):
    if row['representation']=='instance':return leaves(row['geometry_data']['definition_geometry'])
    if row['representation']=='group':return [leaf for member in row['geometry_data']['members'] for leaf in leaves(member)]
    return [row]
def plane_point(row,u,v):
    d=row['geometry_data']
    p=App.Vector(*d['origin_xyz'])+App.Vector(*d['axes_xyz'][0])*u+App.Vector(*d['axes_xyz'][1])*v
    return transformed(row['local_to_world'],p)
def run():
    try:
        import OpenMatrix9Gui as native
        report['module']=native.__file__;Gui.activateWorkbench('OpenMatrix9Workbench')
        doc=App.newDocument('InstanceDefinitions');doc.UndoMode=1
        curve=Part.BezierCurve();curve.setPoles([App.Vector(1,2,3),App.Vector(4,6,8),App.Vector(9,3,7)]);curve.setWeight(2,.5)
        unrelated=doc.addObject('App::Part','Unrelated');unrelated.Placement=place(500,600,700,47)
        definition=doc.addObject('App::Part','Definition');unrelated.addObject(definition);definition.Placement=place(11,13,17,23)
        member=doc.addObject('Part::Feature','Member');definition.addObject(member);member.Shape=curve.toShape();member.Placement=place(2,4,6,31);member.Label='Canonical member'
        inner=doc.addObject('App::Part','Inner');definition.addObject(inner);inner.Placement=place(3,-7,2,41)
        second=doc.addObject('Part::Feature','Second');inner.addObject(second);second.Shape=curve.toShape();second.Placement=place(-3,2,8,17)
        shared=doc.addObject('App::Link','Shared');inner.addObject(shared);shared.setLink(member);shared.LinkTransform=True;shared.LinkPlacement=place(9,-2,5,29);shared.ScaleVector=App.Vector(.7,1.2,2)
        plain=doc.addObject('App::DocumentObjectGroup','Plain');definition.addObject(plain)
        plain_member=doc.addObject('Part::Feature','PlainMember');plain.addObject(plain_member);plain_member.Shape=curve.toShape();plain_member.Placement=place(5,1,3,13)
        empty=doc.addObject('App::Part','Empty');definition.addObject(empty)
        parent=doc.addObject('App::Part','InstanceParent');parent.Placement=place(19,23,29,37)
        a=doc.addObject('App::Link','A');parent.addObject(a);a.setLink(definition);a.LinkTransform=True;a.LinkPlacement=place(31,-4,6,19);a.ScaleVector=App.Vector(-2,3,.5);a.Label='Instance A'
        b=doc.addObject('App::Link','B');parent.addObject(b);b.setLink(definition);b.LinkTransform=False;b.LinkPlacement=place(-11,5,9,43)
        doc.recompute();before=native_state(doc)
        row=json.loads(native.geometryDescriptor(doc.Name,a.Name));report['descriptors']['A']=row
        child=row['geometry_data']['definition_geometry'];check('group definition retained as canonical hierarchy',row['representation']=='instance' and child['representation']=='group' and child['geometry_data']['kind']=='group_definition')
        check('ordered native members preserved',[m['object_name'] for m in child['geometry_data']['members']]==[o.Name for o in definition.Group])
        check('empty group is inspected empty',child['geometry_data']['members'][-1]['geometry_data']['members']==[])
        graph=child['geometry_data']['definition_graph'];check('graph preserves repeated identity occurrences',len(graph['nodes'])>=9 and any(n['representation']=='instance' for n in graph['nodes']))
        # GeoFeatureGroup also retains PlainMember as a direct member when it is
        # added to the ordinary group. Both native membership paths are real.
        samples=leaves(row);check('shared members appear as separate occurrences',len(samples)==5 and sum(r['object_name']==member.Name for r in samples)==2 and sum(r['object_name']==plain_member.Name for r in samples)==2)
        target,path=a.getLinkedObject(True,App.Matrix(),True);check('native link target remains canonical definition',target==definition)
        root_world=parent.getGlobalPlacement().toMatrix().multiply(path)
        expected_paths=[member.Name+'.',inner.Name+'.'+second.Name+'.',inner.Name+'.'+shared.Name+'.',plain.Name+'.'+plain_member.Name+'.',plain_member.Name+'.']
        for descriptor,sub in zip(samples,expected_paths):
            source,member_path=definition.getSubObject(sub,1,App.Matrix(),False)
            source,member_path=source.getLinkedObject(True,member_path,False)
            for t in [.1,.5,.9]:
                expected=root_world.multVec(member_path.multVec(curve.value(t)))
                check(sub+' native world sample matches owned tree',(owned_point(descriptor,t)-expected).Length<1e-8)
        check('source tree and history unchanged by inspection',native_state(doc)==before)
        direct=json.loads(native.geometryDescriptor(doc.Name,definition.Name));report['descriptors']['direct_group']=direct
        check('direct group frame includes actual external ancestor',direct['local_to_world']!=child['local_to_world'] and 'definition_geometry' not in direct['geometry_data'])
        selected_group=json.loads(native.geometryDescriptor(doc.Name,definition.Name,inner.Name+'.'+second.Name+'.'))
        report['descriptors']['selected_group']=selected_group
        check('root group member selection retains hierarchy',selected_group['geometry_data']['kind']=='group_reference' and len(leaves(selected_group))==1 and leaves(selected_group)[0]['object_name']==second.Name)
        target,relative=definition.getSubObject(inner.Name+'.'+second.Name+'.',1,App.Matrix(),False)
        for t in [.2,.7]:check('selected group world matches actual external ancestors',(owned_point(leaves(selected_group)[0],t)-definition.getGlobalPlacement().multVec(relative.multVec(curve.value(t)))).Length<1e-8)
        member_link=doc.addObject('App::Link','MemberLink');parent.addObject(member_link);member_link.setLink(definition,inner.Name+'.'+second.Name+'.');member_link.LinkTransform=True;member_link.LinkPlacement=place(7,11,13,29);doc.recompute()
        selected=json.loads(native.geometryDescriptor(doc.Name,member_link.Name));report['descriptors']['member_link']=selected
        leaf=selected['geometry_data']['definition_geometry'];target,path=member_link.getLinkedObject(True,App.Matrix(),True)
        check('member reference owns actual child identity',target==second and leaf['object_name']==second.Name)
        for t in [.2,.7]:check('member path world placement matches native',(owned_point(leaf,t)-parent.getGlobalPlacement().multVec(path.multVec(curve.value(t)))).Length<1e-8)
        solid_shape=Part.makeBox(2,3,4);solid=doc.addObject('Part::Feature','Solid');definition.addObject(solid);solid.Shape=solid_shape;solid.Placement=place(4,6,8,11)
        face_link=doc.addObject('App::Link','FaceLink');parent.addObject(face_link);face_link.setLink(solid,'Face1');face_link.LinkTransform=True;face_link.LinkPlacement=place(17,19,23,31);doc.recompute()
        face_row=json.loads(native.geometryDescriptor(doc.Name,face_link.Name));report['descriptors']['face_link']=face_row;face=face_row['geometry_data']['definition_geometry']
        check('single subelement is retained rather than whole solid',face['representation']=='trimmed_face' and face['subelement']=='Face1' and face_row['geometry_data']['definition_ref']['subelement']=='Face1')
        multiple=doc.addObject('App::Link','MultiFace');parent.addObject(multiple);multiple.setLink(solid,'',['Face1','Face3']);multiple.LinkTransform=True;multiple.LinkPlacement=place(-13,5,7,19);doc.recompute()
        multi=json.loads(native.geometryDescriptor(doc.Name,multiple.Name));report['descriptors']['multi_face']=multi
        check('multiple selected faces remain distinct ordered references',[r['subelement'] for r in multi['geometry_data']['definition_geometry']['geometry_data']['members']]==['Face1','Face3'])
        for owner,descriptor in [(face_link,face_row),(multiple,multi)]:
            target,path=owner.getLinkedObject(True,App.Matrix(),True)
            for selected_face in leaves(descriptor):
                native_face=solid_shape.Faces[int(selected_face['subelement'][4:])-1]
                u0,u1,v0,v1=native_face.ParameterRange
                for f in [.2,.7]:
                    u=u0+(u1-u0)*f;v=v0+(v1-v0)*(1-f)
                    expected=parent.getGlobalPlacement().multVec(path.multVec(native_face.Surface.value(u,v)))
                    check(owner.Name+' '+selected_face['subelement']+' native surface world sample',(plane_point(selected_face,u,v)-expected).Length<1e-8)
        before=native_state(doc)
        for owner,sub in [(definition,'Missing.'),(definition,inner.Name+'.Missing.'),(a,'Face999'),(solid,'Face999'),(definition,'x'*4097)]:
            rejected=False
            try:native.geometryDescriptor(doc.Name,owner.Name,sub)
            except (ValueError,RuntimeError):rejected=True
            check('malformed '+owner.Name+' '+sub[:25]+' rejects atomically',rejected and native_state(doc)==before)
        deep=doc.addObject('App::DocumentObjectGroup','Deep');at=deep
        for i in range(64):
            next_group=doc.addObject('App::DocumentObjectGroup','Depth'+str(i));at.addObject(next_group);at=next_group
        doc.recompute();before=native_state(doc);rejected=False
        try:native.geometryDescriptor(doc.Name,deep.Name)
        except (ValueError,RuntimeError):rejected=True
        check('native 65-level definition rejects without mutation',rejected and native_state(doc)==before)
        # The budget must reject the already-oversized container prefix before
        # traversing an unsupported sentinel. Checking final JSON only is late.
        large=doc.addObject('App::DocumentObjectGroup','LargeMetadata')
        for i in range(70):
            item=doc.addObject('App::DocumentObjectGroup','Metadata'+str(i));large.addObject(item)
            prefix=str(i)+':';item.Label=prefix+'x'*(65536-len(prefix))
            if 'Label2' not in item.PropertiesList:item.addProperty('App::PropertyString','Label2')
            item.Label2='y'*65536
        sentinel=doc.addObject('App::FeaturePython','UnsupportedAfterBudget');large.addObject(sentinel);doc.recompute()
        before=native_state(doc);error=''
        try:native.geometryDescriptor(doc.Name,large.Name)
        except (ValueError,RuntimeError) as failure:error=str(failure)
        report['container_budget_error']=error
        check('container metadata budget rejects before later unsupported leaf','serialized payload budget' in error and native_state(doc)==before)
        old_a=json.loads(native.geometryDescriptor(doc.Name,a.Name));canonical=native_state(doc)['shapes'];doc.openTransaction('Move B');b.LinkPlacement=place(100,200,300,47);doc.recompute();doc.commitTransaction()
        now_a=json.loads(native.geometryDescriptor(doc.Name,a.Name));check('editing B preserves live A and canonical shapes',now_a['local_to_world']==old_a['local_to_world'] and [r['local_to_world'] for r in leaves(now_a)]==[r['local_to_world'] for r in leaves(old_a)] and native_state(doc)['shapes']==canonical)
        moved=json.loads(native.geometryDescriptor(doc.Name,b.Name));doc.undo();doc.recompute();undone=json.loads(native.geometryDescriptor(doc.Name,b.Name));check('Undo changes B back',moved['local_to_world']!=undone['local_to_world']);doc.redo();doc.recompute();check('Redo restores B',json.loads(native.geometryDescriptor(doc.Name,b.Name))['local_to_world']==moved['local_to_world'])
        saved=json.dumps(report['descriptors'],sort_keys=True);member.Shape=Part.makeBox(1,1,1);doc.recompute();App.closeDocument(doc.Name);check('owned group/refs survive replacement and document close',json.dumps(report['descriptors'],sort_keys=True)==saved)
        report['ok']=True
    except Exception:report['ok']=False;report['error']=traceback.format_exc()
    finally:
        (out/'results.json').write_text(json.dumps(report,indent=2))
        for name in list(App.listDocuments()):App.closeDocument(name)
        Gui.getMainWindow().close()
QtCore.QTimer.singleShot(1200,run)
