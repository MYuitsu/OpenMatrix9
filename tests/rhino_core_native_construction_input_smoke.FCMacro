"""Real GUI input-boundary regression for existing Surface and Rebuild paths."""
import json, os, traceback
from pathlib import Path
import FreeCAD as App, FreeCADGui as Gui, Part, OpenMatrix9Gui
from PySide6 import QtCore, QtGui, QtWidgets

out = Path(os.environ['OM9_SMOKE_OUTPUT'])
report = {'checks': [], 'module': OpenMatrix9Gui.__file__, 'diagnostics': []}

def check(name, value):
    report['checks'].append({'name': name, 'passed': bool(value)})

def events():
    QtWidgets.QApplication.processEvents()

def enter(text=''):
    console.setFocus()
    QtWidgets.QApplication.sendEvent(console, QtGui.QKeyEvent(
        QtCore.QEvent.KeyPress, QtCore.Qt.Key_End, QtCore.Qt.ControlModifier))
    if text:
        QtWidgets.QApplication.sendEvent(console, QtGui.QKeyEvent(
            QtCore.QEvent.KeyPress, 0, QtCore.Qt.NoModifier, text))
    QtWidgets.QApplication.sendEvent(console, QtGui.QKeyEvent(
        QtCore.QEvent.KeyPress, QtCore.Qt.Key_Return, QtCore.Qt.NoModifier))
    events()

def cancel():
    QtWidgets.QApplication.sendEvent(console, QtGui.QKeyEvent(
        QtCore.QEvent.KeyPress, QtCore.Qt.Key_Escape, QtCore.Qt.NoModifier))
    events()

def bad_curve():
    curve = Part.BSplineCurve()
    curve.buildFromPolesMultsKnots(
        [App.Vector(0, 0, 0), App.Vector(1e151, 1, 0), App.Vector(2, 0, 0)],
        [3, 3], [0., 1.], False, 2)
    return curve.toShape()

def feature(doc, name, shape):
    obj = doc.addObject('Part::Feature', name)
    obj.ViewObject.Visibility = False
    obj.Shape = shape
    return obj

def state(doc, obj):
    return (tuple(o.Name for o in doc.Objects), doc.UndoCount, doc.RedoCount,
            obj.Shape.exportBrepToString())

def rejection(operation, command):
    doc = App.newDocument('ConstructionInput' + operation)
    doc.UndoMode = 1
    doc.openTransaction('Sources')
    obj = feature(doc, 'BadCurve', bad_curve())
    doc.commitTransaction()
    doc.openTransaction('Redo witness')
    obj.Label = 'Executable Redo'
    doc.commitTransaction()
    doc.undo()
    before = state(doc, obj)
    console.clear()
    Gui.Selection.clearSelection()
    Gui.Selection.addSelection(obj)
    if command:
        Gui.runCommand(command, 0)
        events()
    else:
        enter(operation)
    diagnostic = console.toPlainText()
    report['diagnostics'].append({'operation': operation, 'text': diagnostic})
    check(operation + ' rejects malformed native basis with operation and identity',
          all(token in diagnostic for token in ('InvalidBasis', operation, 'BadCurve')))
    check(operation + ' rejection preserves geometry objects Undo and Redo', state(doc, obj) == before)
    cancel()
    doc.redo()
    check(operation + ' rejection preserves executable Redo', obj.Label == 'Executable Redo')
    App.closeDocument(doc.Name)

def selected_edge():
    doc = App.newDocument('SelectedConstructionEdge')
    doc.UndoMode = 1
    good = Part.makeLine(App.Vector(0, 0, 0), App.Vector(8, 0, 0))
    owner = feature(doc, 'MixedOwner', Part.makeCompound([bad_curve(), good]))
    other = feature(doc, 'Other', Part.makeLine(App.Vector(0, 0, 10), App.Vector(8, 0, 10)))
    before = state(doc, owner)
    Gui.Selection.clearSelection()
    Gui.Selection.addSelection(doc.Name, owner.Name, 'Edge2')
    Gui.Selection.addSelection(other)
    Gui.runCommand('OM9_SurfaceLoft', 0)
    events()
    enter()
    panel = next((w for w in Gui.getMainWindow().findChildren(QtWidgets.QDialog, 'OM9SurfaceOptions')
                  if w.isVisible()), None)
    check('Loft retains valid selected-edge behavior with an unselected sibling', panel is not None)
    check('Loft valid selected-edge preview remains acceptable', panel is not None and
          panel.findChild(QtWidgets.QDialogButtonBox).button(QtWidgets.QDialogButtonBox.Ok).isEnabled())
    cancel()
    check('Loft selected-edge preview and cancellation preserve the whole source', state(doc, owner) == before)
    App.closeDocument(doc.Name)

def run():
    global console
    try:
        Gui.activateWorkbench('OpenMatrix9Workbench')
        events()
        console = Gui.getMainWindow().findChild(QtWidgets.QPlainTextEdit, 'OM9CommandTranscript')
        rejection('Sweep1', 'OM9_SurfaceSweepSweep1Rail')
        rejection('Loft', 'OM9_SurfaceLoft')
        rejection('Rebuild', None)
        selected_edge()
        report['ok'] = all(c['passed'] for c in report['checks'])
    except Exception:
        report['ok'] = False
        report['error'] = traceback.format_exc()
    finally:
        for name in list(App.listDocuments()):
            App.closeDocument(name)
        (out / 'results.json').write_text(json.dumps(report, indent=2), encoding='utf-8')
        QtCore.QTimer.singleShot(100, Gui.getMainWindow().close)

QtCore.QTimer.singleShot(1200, run)
