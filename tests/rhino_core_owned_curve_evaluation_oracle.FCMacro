# SPDX-License-Identifier: LGPL-2.1-or-later
"""Native values/D1 for owned curve basis; no OM9 evaluation implementation."""
import json,math,os,traceback
from pathlib import Path
import FreeCAD as App,FreeCADGui as Gui,Part,OpenMatrix9Gui as native
from PySide6 import QtCore
out=Path(os.environ['OM9_SMOKE_OUTPUT']);report=dict(module=native.__file__,checks=[],cases=[])
def xyz(p):return [p.x,p.y,p.z]
def check(name,value):
    report['checks'].append(dict(name=name,passed=bool(value)))
    if not value:raise AssertionError(name)
def spline(poles,mults,knots,periodic,degree,weights=None):
    c=Part.BSplineCurve()
    args=([App.Vector(*p)for p in poles],mults,knots,periodic,degree)
    if weights is None:c.buildFromPolesMultsKnots(*args)
    else:c.buildFromPolesMultsKnots(*args,weights)
    return c
def run():
    try:
        Gui.activateWorkbench('OpenMatrix9Workbench');doc=App.newDocument('OwnedCurveOracle');doc.UndoMode=1
        triangle=[[0,0,0],[1,2,0],[2,0,0]]
        cases=[
            ('RationalArc',spline([[10,0,0],[10,10,0],[0,10,0]],[3,3],[0,1],False,2,[1,math.sqrt(.5),1])),
            ('Unclamped',spline([[0,0,0],[1,2,1],[3,1,2]],[1]*6,[0,1,2,3,4,5],False,2)),
            ('RepeatedInterior',spline([[0,0,0],[1,2,1],[2,3,0],[3,1,2],[4,0,1],[5,2,3],[6,1,0]],[4,2,1,4],[0,1,2,3],False,3,[1,2,.5,3,1,.75,2])),
            ('PeriodicLinear',spline(triangle,[1]*4,[0,1,2,3],True,1)),
            ('PeriodicQuadratic',spline(triangle,[1]*4,[0,1,2,3],True,2)),
            ('PeriodicRational',spline(triangle,[1]*4,[0,1,2,3],True,2,[1,2,.5])),
            ('PeriodicRepeatedSeam',spline([[0,0,0],[2,0,1],[3,2,0],[1,4,1],[-1,2,0]],[2,1,2,2],[0,1,2,3],True,3,[1,2,.5,1.5,1])),
            ('NativeRationalCircle',Part.makeCircle(10).toNurbs().Edges[0].Curve),
        ]
        bezier=Part.BezierCurve();bezier.setPoles([App.Vector(10,0,0),App.Vector(10,10,0),App.Vector(0,10,0)]);bezier.setWeight(2,math.sqrt(.5))
        cases.append(('RationalBezier',bezier))
        for name,curve in cases:
            obj=doc.addObject('Part::Feature',name);obj.Shape=curve.toShape();doc.recompute()
            before=obj.Shape.exportBrepToString();counts=(doc.UndoCount,doc.RedoCount)
            descriptor=json.loads(native.geometryDescriptor(doc.Name,obj.Name));data=descriptor['geometry_data']
            check(name+' complete owned basis',data['kind']in ('nurbs_curve','bezier_curve')and data['poles_xyz'])
            edge=obj.Shape.Edges[0];lo,hi=edge.FirstParameter,edge.LastParameter
            parameters=[lo+(hi-lo)*f for f in [0,.001,.125,.25,.5,.75,.875,.999,1]]
            if data['kind']=='nurbs_curve':parameters+= [u for u in data['axis']['knots']if lo<=u<=hi]
            parameters=sorted(set(parameters))
            queries=[dict(parameter=u,value=xyz(edge.valueAt(u)),derivative=xyz(edge.derivative1At(u)))for u in parameters]
            check(name+' finite independent OCCT values and D1',all(math.isfinite(v)for q in queries for key in ('value','derivative')for v in q[key]))
            check(name+' leaves exact source and Undo/Redo untouched',before==obj.Shape.exportBrepToString()and counts==(doc.UndoCount,doc.RedoCount))
            report['cases'].append(dict(name=name,geometry_data=data,domain=[lo,hi],queries=queries))
        check('all nine curve families captured',len(report['cases'])==9)
        report['ok']=True
    except Exception:report['ok']=False;report['error']=traceback.format_exc()
    finally:
        (out/'results.json').write_text(json.dumps(report,indent=2),encoding='utf-8')
        for name in list(App.listDocuments()):App.closeDocument(name)
        QtCore.QTimer.singleShot(100,Gui.getMainWindow().close)
QtCore.QTimer.singleShot(1200,run)
