# SPDX-License-Identifier: LGPL-2.1-or-later
"""Error cleanup must retire its inverse before reporting completion."""
import json, os, sys, traceback
from pathlib import Path
import FreeCAD as App, FreeCADGui as Gui, OpenMatrix9Gui as OM
from PySide6 import QtCore

out = Path(os.environ['OM9_SMOKE_OUTPUT'])
report = dict(module=OM.__file__, checks=[], observations=[])
sys.path.insert(0, os.environ['OM9_REPLAY_RETIREMENT_PROBE'])
import OM9ReplayRetirement as probe

def check(name, passed):
    report['checks'].append(dict(name=name, passed=bool(passed)))

def run():
    try:
        Gui.activateWorkbench('OpenMatrix9Workbench')
        for preserving in (False, True):
            events = []
            doc = App.newDocument('CleanupVerdict%d' % preserving)
            doc.UndoMode = 1
            child = doc.getObject(probe.create(doc.Name))
            child.addProperty('App::PropertyPythonObject', 'Payload')
            class LastValue:
                def __del__(self):
                    events.append('started')
                    try: child.Value = 'tampered'; events.append('changed')
                    except Exception as error: events.append(str(error))
            child.Payload = LastValue()
            doc.recompute()
            doc.clearUndos()
            if preserving: doc.openTransactionPreservingRedo('caller')
            else: doc.openTransaction('caller')
            result = probe.run(doc.Name, 'value', 'python_cleanup', None)
            prefix = 'preserving%d: ' % preserving
            check(prefix + 'open notification rejection is observed', 'native open notification failed' in result['error'] and not result['accepted'])
            check(prefix + 'native rollback completed before error cleanup', result['rollback'])
            check(prefix + 'actual last-reference finalizer ran', len(events) == 2 and events[0] == 'started')
            check(prefix + 'late mutation blocked by typed barrier', len(events) == 2 and 'StaleGeometry' in events[1])
            check(prefix + 'late error cleanup violation prevents completion', not result['complete'])
            check(prefix + 'retry cannot report completion after rejected final retirement', not result['cleanup_retry_complete'])
            check(prefix + 'restored scalar and invalid output survive attempted mutation', child.Value == 'original-value' and child.Output == '')
            report['observations'].append(dict(preserving=preserving, result=result, events=list(events)))
            doc.abortTransaction()
        report['ok'] = all(c['passed'] for c in report['checks'])
    except Exception:
        report['ok'] = False
        report['error'] = traceback.format_exc()
    finally:
        (out/'results.json').write_text(json.dumps(report, indent=2))
        for name in list(App.listDocuments()): App.closeDocument(name)
        QtCore.QTimer.singleShot(100, Gui.getMainWindow().close)

QtCore.QTimer.singleShot(1000, run)
