# SPDX-License-Identifier: LGPL-2.1-or-later
"""A separate host reopens and independently checks saved focus CAD masters."""
import json,os,traceback
from pathlib import Path
import FreeCAD as App,FreeCADGui as Gui,Part,OpenMatrix9Gui as OM
from PySide6 import QtCore
out=Path(os.environ['OM9_SMOKE_OUTPUT']);report=dict(module=OM.__file__,checks=[],observations=[])
def check(name,value):report['checks'].append(dict(name=name,passed=bool(value)))
def run():
 try:
  directory=Path(os.environ['OM9_FOCUS_ARCHIVE_DIR']);warm=json.loads((directory/'results.json').read_text())
  for observation in warm['observations']:
   doc=App.openDocument(observation['archive']);center=observation['center'];x,y,z=center
   for i,raw in enumerate(observation['results']):
    label=str(center)+'/Focus'+str(i+1);obj=doc.getObject('EllipseFocus'+str(i+1));value=json.loads(obj.OM9GeometryResult);snapshot=value['output_snapshots'][0]
    check(label+' exact paired bytes after cold open',bool(raw)and obj.OM9GeometryResult==raw and json.loads(obj.OM9CurveConstruction)==value['operation_context']['construction'])
    check(label+' focus role original points and units',value['operation_context']['output_role']=='ellipse_focus'+str(i+1)and value['input_snapshots'][0]['geometry_data']['points_xyz']==[[x-4,y,z],[x+4,y,z],[x,y+3,z]]and snapshot['unit_context_snapshot']==obj.OM9UnitContext)
    shape=Part.Shape();shape.importBrepFromString(snapshot['geometry_data']['native_master']['payload'])
    expected=App.Vector(x+[-4.,4.][i],y,z)
    check(label+' full native point and independent position',shape.isValid()and shape.ShapeType=='Vertex'and (shape.Vertexes[0].Point-expected).Length<1e-7 and (obj.Shape.Vertexes[0].Point-expected).Length<1e-7)
    report['observations'].append(dict(case=label,raw=obj.OM9GeometryResult))
   App.closeDocument(doc.Name)
  report['ok']=all(c['passed']for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
