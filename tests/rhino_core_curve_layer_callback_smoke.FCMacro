# SPDX-License-Identifier: LGPL-2.1-or-later
"""Curve publication requires the selected layer, its metadata and unchanged output permissions."""
import json,math,os,traceback
from pathlib import Path
import FreeCAD as App,FreeCADGui as Gui,Part,OpenMatrix9Gui as OM
from PySide6 import QtCore,QtGui,QtWidgets
out=Path(os.environ['OM9_SMOKE_OUTPUT']);report=dict(module=OM.__file__,checks=[],observations=[])
def check(name,value):report['checks'].append(dict(name=name,passed=bool(value)))
def enter(console,text):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier))
def settle():
 loop=QtCore.QEventLoop();QtCore.QTimer.singleShot(80,loop.quit);loop.exec()
def snapshot(doc):
 return dict(objects=[dict(name=o.Name,label=o.Label,shape=o.Shape.exportBrepToString()if 'Shape'in o.PropertiesList else None,
  placement=list(o.Placement.toMatrix().A)if 'Placement'in o.PropertiesList else None,
  members=[m.Name for m in o.Group]if 'Group'in o.PropertiesList else None,
  layer_locked=getattr(o,'OM9LayerLocked',None),unit_context=getattr(o,'Context',None))for o in doc.Objects],undo=doc.UndoCount,redo=doc.RedoCount)
def physical(obj,command):
 if obj is None or obj.Shape.isNull()or not obj.Shape.isValid():return False
 if command=='Ellipse':
  c=obj.Shape.Edges[0].Curve
  return isinstance(c,Part.Ellipse)and abs(c.MajorRadius-5)<1e-7 and abs(c.MinorRadius-3)<1e-7 and c.Center.Length<1e-7
 return abs(obj.Shape.Length-{'Line':10.,'Polyline':12.,'Rectangle':14.,'Circle':4*math.pi,'InterpCrv':7.}[command])<1e-7
CASES=[('Line',['0,0,0'],'10,0,0'),('Polyline',['0,0,0','3,0,0','3,4,0'],'Close'),
 ('Rectangle',['0,0,0'],'4,3,0'),('Circle',['0,0,0'],'Radius=2'),
 ('Ellipse',['0,0,0','5,0,0'],'0,3,0'),('InterpCrv',['Degree=1','0,0,0','3,0,0','3,4,0'],'')]
class Observer:
 def __init__(self,doc,console,command,action):self.doc=doc.Name;self.console=console;self.command=command;self.action=action;self.calls=0;self.armed=True
 def matches(self,obj):return self.armed and obj.Document.Name==self.doc and obj.Name.startswith(self.command)
 def slotCreatedObject(self,obj):
  if self.action=='restart-same'and self.matches(obj):
   self.armed=False;self.calls+=1;enter(self.console,self.command)
 def slotChangedObject(self,obj,prop):
  if self.action=='restart-same'or not self.matches(obj)or prop!='OM9GeometryResult'or not getattr(obj,prop,''):return
  self.armed=False;self.calls+=1
  layer=next(o for o in obj.Document.Objects if getattr(o,'OM9LayerIndex',0)==1 and getattr(o,'OM9LayerSchema',0))
  if self.action=='detach':layer.removeObject(obj)
  elif self.action=='index':obj.OM9OutputLayerIndex=2
  elif self.action=='layer-lock':layer.OM9LayerLocked=True
  elif self.action=='unit-context':obj.Document.getObject('OM9Units').Context='invalid unit context'
  elif self.action=='hide':obj.ViewObject.Visibility=False
  elif self.action=='color':obj.ViewObject.LineColor=(1.,0.,0.)
  elif self.action=='selectable':obj.ViewObject.Selectable=False

def case(console,command,prefix,final,action):
 label=command+'/'+action;doc=App.newDocument('CurveCallback'+command+action.replace('-',''));observer=None
 try:
  doc.UndoMode=1;OM.setUnitContext(doc.Name,1.,1.,.01,.001,.01)
  enter(console,'Layer=1');settle()
  witness=doc.addObject('App::FeaturePython','Witness')
  if action=='parent':
   parent=doc.addObject('App::Part','Parent');parent.Placement.Base=App.Vector(20,30,40)
  doc.recompute();doc.openTransaction('Prior executable Redo');witness.Label='Prior Redo executes';doc.commitTransaction();doc.undo();settle()
  console.clear();enter(console,command)
  for text in prefix:enter(console,text)
  before=snapshot(doc);observer=Observer(doc,console,command,action);App.addDocumentObserver(observer)
  enter(console,final);settle();calls=observer.calls;App.removeDocumentObserver(observer);observer=None
  after=snapshot(doc);diagnostic=console.toPlainText()
  check(label+' real native callback once',calls==1)
  check(label+' complete document and Undo and prior Redo unchanged',before==after and before['redo']==1)
  rejected=doc.getObject(command)is None
  check(label+' no rejected output remains',rejected)
  check(label+' typed diagnostic identifies actual operation',any('StaleGeometry:'in line and command in line for line in diagnostic.splitlines()))
  if action=='restart-same':
   for text in prefix:enter(console,text)
   enter(console,final);settle();obj=doc.getObject(command)
   check(label+' callback replacement session completes independently',rejected and before==after and physical(obj,command)and bool(getattr(obj,'OM9GeometryResult',''))and doc.UndoCount==before['undo']+1)
  else:
   executed=False
   if doc.RedoCount:doc.redo();executed=witness.Label=='Prior Redo executes'
   check(label+' prior native Redo still executes',executed)
  report['observations'].append(dict(case=label,before=before,after=after,calls=calls,diagnostic=diagnostic))
 finally:
  if observer:App.removeDocumentObserver(observer)
  enter(console,'Cancel');App.closeDocument(doc.Name)
def run():
 try:
  Gui.activateWorkbench('OpenMatrix9Workbench');settle();console=Gui.getMainWindow().findChild(QtWidgets.QPlainTextEdit,'OM9CommandTranscript')
  for command,prefix,final in CASES:
   for action in ['detach','index','layer-lock','unit-context','hide','color','selectable']:case(console,command,prefix,final,action)
  report['ok']=all(c['passed']for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
