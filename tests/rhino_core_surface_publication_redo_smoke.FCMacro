# SPDX-License-Identifier: LGPL-2.1-or-later
"""Surface publication failure must preserve executable prior Redo with/without History."""
import json
import os
import traceback
from pathlib import Path
import FreeCAD as App
import FreeCADGui as Gui
import Part
import OpenMatrix9Gui as OM
from PySide6 import QtCore, QtGui, QtWidgets

out = Path(os.environ['OM9_SMOKE_OUTPUT'])
report = dict(module=OM.__file__, checks=[], observations=[])


def check(name, value):
    report['checks'].append(dict(name=name, passed=bool(value)))


def events():
    QtWidgets.QApplication.processEvents()


def enter(console, text=''):
    console.setFocus()
    QtWidgets.QApplication.sendEvent(console, QtGui.QKeyEvent(
        QtCore.QEvent.KeyPress, QtCore.Qt.Key_End, QtCore.Qt.ControlModifier))
    if text:
        QtWidgets.QApplication.sendEvent(console, QtGui.QKeyEvent(
            QtCore.QEvent.KeyPress, 0, QtCore.Qt.NoModifier, text))
    QtWidgets.QApplication.sendEvent(console, QtGui.QKeyEvent(
        QtCore.QEvent.KeyPress, QtCore.Qt.Key_Return, QtCore.Qt.NoModifier))
    events()


def snapshot(doc):
    return tuple((obj.Name, obj.Label,
                  obj.Shape.exportBrepToString() if 'Shape' in obj.PropertiesList else None)
                 for obj in doc.Objects), doc.UndoCount, doc.RedoCount


class Observer:
    def __init__(self, doc, source):
        self.doc, self.source, self.fired = doc, source, False

    def slotCreatedObject(self, obj):
        if obj.Document == self.doc and not self.fired:
            self.fired = True
            self.source.Shape = Part.makeLine(App.Vector(30, 0, 0), App.Vector(30, 3, 0))


def run_case(kind, history, console):
    label = ['Sweep1', 'Sweep2', 'Loft'][kind-1] + ('History' if history else 'Plain')
    doc = App.newDocument('SurfacePublication' + label)
    observer = None
    try:
        doc.UndoMode = 1
        sources = []
        def line(name, a, b):
            obj = doc.addObject('Part::Feature', name)
            obj.Shape = Part.makeLine(App.Vector(*a), App.Vector(*b))
            sources.append(obj)
        if kind == 3:
            line('First', (0, 0, 0), (0, 3, 0))
            line('Last', (10, 0, 0), (10, 3, 0))
        else:
            line('Rail', (0, 0, 0), (10, 0, 0))
            if kind == 2:
                line('SecondRail', (0, 3, 0), (10, 3, 0))
            line('Profile', (0, 0, 0), (0, 3, 0))
        witness = doc.addObject('App::FeaturePython', 'Witness')
        doc.recompute()
        doc.openTransaction('Executable prior Redo')
        witness.Label = 'Executable Redo'
        doc.commitTransaction()
        doc.undo()
        before = snapshot(doc)
        Gui.Selection.clearSelection()
        for obj in sources:
            Gui.Selection.addSelection(obj)
        console.clear()
        Gui.runCommand(['OM9_SurfaceSweepSweep1Rail', 'OM9_SurfaceSweepSweep2Rails',
                        'OM9_SurfaceLoft'][kind-1])
        events()
        enter(console)
        dialog = next(widget for widget in Gui.getMainWindow().findChildren(
            QtWidgets.QDialog, 'OM9SurfaceOptions') if widget.isVisible())
        dialog.findChild(QtWidgets.QCheckBox, 'OM9SurfaceHistory').setChecked(history)
        observer = Observer(doc, sources[-1])
        App.addDocumentObserver(observer)
        try:
            dialog.findChild(QtWidgets.QDialogButtonBox).button(QtWidgets.QDialogButtonBox.Ok).click()
            events()
        finally:
            App.removeDocumentObserver(observer)
        after = snapshot(doc)
        error = console.toPlainText()
        report['observations'].append(dict(case=label, callback=observer.fired, error=error,
            before_undo=before[1], after_undo=after[1], before_redo=before[2], after_redo=after[2],
            objects_restored=before[0] == after[0]))
        check(label + ' real output callback invalidates source', observer.fired)
        check(label + ' reports typed operation and selected source',
              any('StaleGeometry' in line and sources[-1].Name in line
                  and ['Sweep1', 'Sweep2', 'Loft'][kind-1] in line for line in error.splitlines()))
        check(label + ' abort restores geometry objects and Undo',
              before[0] == after[0] and before[1] == after[1])
        check(label + ' abort retains prior Redo count', before[2] == after[2] == 1)
        enter(console, 'Cancel')
        if doc.RedoCount:
            doc.redo()
        check(label + ' prior Redo remains executable', witness.Label == 'Executable Redo')
    finally:
        if observer is not None:
            try:
                App.removeDocumentObserver(observer)
            except Exception:
                pass
        App.closeDocument(doc.Name)


def run():
    try:
        Gui.activateWorkbench('OpenMatrix9Workbench')
        events()
        console = Gui.getMainWindow().findChild(QtWidgets.QPlainTextEdit, 'OM9CommandTranscript')
        for kind in [1, 2, 3]:
            for history in [False, True]:
                run_case(kind, history, console)
        report['ok'] = all(row['passed'] for row in report['checks'])
    except Exception:
        report['ok'] = False
        report['error'] = traceback.format_exc()
    finally:
        (out / 'results.json').write_text(json.dumps(report, indent=2), encoding='utf-8')
        QtCore.QTimer.singleShot(100, Gui.getMainWindow().close)


QtCore.QTimer.singleShot(1200, run)
