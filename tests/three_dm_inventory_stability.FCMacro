import FreeCADGui as Gui,json,os,traceback
from pathlib import Path
from PySide6 import QtCore
out=Path(os.environ['OM9_SMOKE_OUTPUT'])
def run():
    try:
        Gui.activateWorkbench('OpenMatrix9Workbench');import OpenMatrix9Gui as native
        source=str(Path(__file__).parent/'fixtures/3dm/Oval-twist-ring.3dm')
        first=json.loads(native.inspect3dm(source));second=json.loads(native.inspect3dm(source))
        (out/'first.json').write_text(json.dumps(first,indent=2));(out/'second.json').write_text(json.dumps(second,indent=2))
        (out/'results.json').write_text(json.dumps(dict(ok=first==second,checks=[dict(name='inventory deterministic',passed=first==second)],different_keys=[k for k in first if first[k]!=second[k]])))
    except Exception:(out/'results.json').write_text(json.dumps(dict(ok=False,error=traceback.format_exc())))
    QtCore.QTimer.singleShot(100,Gui.getMainWindow().close)
QtCore.QTimer.singleShot(1000,run)
