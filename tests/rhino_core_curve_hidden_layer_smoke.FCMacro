# SPDX-License-Identifier: LGPL-2.1-or-later
"""Real Curve callbacks must not publish changed outputs or erase prior Redo."""
import json,math,os,traceback
from pathlib import Path
import FreeCAD as App,FreeCADGui as Gui,Part,OpenMatrix9Gui as OM
from PySide6 import QtCore,QtGui,QtWidgets
out=Path(os.environ['OM9_SMOKE_OUTPUT']);report=dict(module=OM.__file__,checks=[],observations=[])
def check(name,value):report['checks'].append(dict(name=name,passed=bool(value)))
def enter(console,text):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier))
def settle():
 loop=QtCore.QEventLoop();QtCore.QTimer.singleShot(80,loop.quit);loop.exec()
def snapshot(doc):
 return dict(objects=[dict(name=o.Name,label=o.Label,shape=o.Shape.exportBrepToString()if 'Shape'in o.PropertiesList else None,
  placement=list(o.Placement.toMatrix().A)if 'Placement'in o.PropertiesList else None,
  members=[m.Name for m in o.Group]if 'Group'in o.PropertiesList else None)for o in doc.Objects],undo=doc.UndoCount,redo=doc.RedoCount)
def physical(obj,command):
 if obj is None or obj.Shape.isNull()or not obj.Shape.isValid():return False
 if command=='Ellipse':
  c=obj.Shape.Edges[0].Curve
  return isinstance(c,Part.Ellipse)and abs(c.MajorRadius-5)<1e-7 and abs(c.MinorRadius-3)<1e-7 and c.Center.Length<1e-7
 return abs(obj.Shape.Length-{'Line':10.,'Polyline':12.,'Rectangle':14.,'Circle':4*math.pi,'InterpCrv':7.}[command])<1e-7
CASES=[('Line',['0,0,0'],'10,0,0'),('Polyline',['0,0,0','3,0,0','3,4,0'],'Close'),
 ('Rectangle',['0,0,0'],'4,3,0'),('Circle',['0,0,0'],'Radius=2'),
 ('Ellipse',['0,0,0','5,0,0'],'0,3,0'),('InterpCrv',['Degree=1','0,0,0','3,0,0','3,4,0'],'')]
def case(console,command,prefix,final,foci=False):
 label=command+('/foci'if foci else '/main');doc=App.newDocument('CurveHiddenLayer'+command+str(foci))
 try:
  doc.UndoMode=1;OM.setUnitContext(doc.Name,1.,1.,.01,.001,.01);enter(console,'Layer=1');settle()
  layer=next(o for o in doc.Objects if getattr(o,'OM9LayerIndex',0)==1 and getattr(o,'OM9LayerSchema',0))
  layer.ViewObject.Visibility=False;doc.recompute();before=doc.UndoCount
  console.clear();enter(console,command)
  if foci:enter(console,'FromFoci');enter(console,'MarkFoci=Yes');prefix=['-4,0,0','4,0,0'];final='0,3,0'
  for value in prefix:enter(console,value)
  enter(console,final);settle();obj=doc.getObject(command)
  outputs=[o for o in doc.Objects if o.Name.startswith(command)]
  check(label+' correct independent main geometry',physical(obj,command))
  check(label+' one complete command Undo',doc.UndoCount==before+1)
  check(label+' all outputs in selected off layer',len(outputs)==(3 if foci else 1)and all(o in layer.Group and getattr(o,'OM9OutputLayerIndex',0)==1 for o in outputs))
  check(label+' invisible output preserves Selectable permission',bool(outputs)and all(not o.ViewObject.Visibility and o.ViewObject.Selectable and o.OM9LayerExplicitSelectable for o in outputs))
  check(label+' main paired construction result units',bool(obj)and bool(obj.OM9GeometryResult)and bool(obj.OM9CurveConstruction)and bool(obj.OM9UnitContext))
  if foci:
   a=doc.getObject('EllipseFocus1');b=doc.getObject('EllipseFocus2')
   check(label+' independent focus coordinates',bool(a and b)and abs(a.Shape.Vertexes[0].Point.Length-4.)<1e-7 and abs(b.Shape.Vertexes[0].Point.Length-4.)<1e-7 and (a.Shape.Vertexes[0].Point+b.Shape.Vertexes[0].Point).Length<1e-7)
  doc.undo();check(label+' Undo removes whole output set',not any(o.Name.startswith(command)for o in doc.Objects))
  doc.redo();check(label+' Redo restores whole layer membership',len([o for o in layer.Group if o.Name.startswith(command)])==(3 if foci else 1))
  report['observations'].append(dict(case=label,diagnostic=console.toPlainText()))
 finally:
  enter(console,'Cancel');App.closeDocument(doc.Name)
def run():
 try:
  Gui.activateWorkbench('OpenMatrix9Workbench');settle();console=Gui.getMainWindow().findChild(QtWidgets.QPlainTextEdit,'OM9CommandTranscript')
  for command,prefix,final in CASES:case(console,command,prefix,final)
  case(console,*CASES[4],True)
  report['ok']=all(c['passed']for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
