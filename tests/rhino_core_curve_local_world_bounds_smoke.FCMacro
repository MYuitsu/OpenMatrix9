# SPDX-License-Identifier: LGPL-2.1-or-later
"""Large retained local basis, valid small world inputs: native policy oracle."""
import json,os,sys,traceback
from pathlib import Path
import FreeCAD as App,FreeCADGui as Gui,Part
from PySide6 import QtCore,QtTest
sys.path.insert(0,os.environ['OM9_FIXTURE_HELPER_DIR'])
from command_console_support import command_input
out=Path(os.environ['OM9_SMOKE_OUTPUT']);report=dict(checks=[])
def check(name,value):report['checks'].append(dict(name=name,passed=bool(value)))
def settle():
 loop=QtCore.QEventLoop();QtCore.QTimer.singleShot(100,loop.quit);loop.exec()
def enter(text):
 field.setFocus();field.setText(text);QtTest.QTest.keyClick(field,QtCore.Qt.Key_Return);settle()
def run():
 global field
 try:
  Gui.activateWorkbench('OpenMatrix9Workbench');import OpenMatrix9Gui as OM
  report['module']=OM.__file__;field=command_input(Gui.getMainWindow());doc=App.newDocument('LocalWorldPolicy');doc.UndoMode=1;OM.setUnitContext(doc.Name,1.,1.,.01,.001,.01)
  settings=doc.addObject('OpenMatrix9Gui::HistorySettings','OM9HistorySettings');settings.BrokenHistoryWarning=False
  vertex=doc.addObject('Part::Feature','LocatedVertex');vertex.Shape=Part.Vertex(App.Vector(1e12+1,45,0));vertex.Placement.Base=App.Vector(-1e12,0,0);doc.recompute()
  enter('Circle');enter('History=Yes');enter('Point=LocatedVertex.Vertex1');enter('Radius=5');child=doc.Objects[-1]
  check('Large local vertex yields valid world center',child.TypeId=='OpenMatrix9Gui::CircleHistory'and not child.Shape.isNull()and(child.Shape.Edges[0].Curve.Center-App.Vector(1,45,0)).Length<1e-7)
  report['vertex_initial']=json.loads(child.OM9GeometryResult);child.touch();doc.recompute()
  check('Vertex History respects local versus world limits',not child.Shape.isNull()and bool(child.OM9GeometryResult))
  if child.OM9GeometryResult:report['vertex_replay']=json.loads(child.OM9GeometryResult)
  c=Part.BSplineCurve();c.buildFromPolesMultsKnots([App.Vector(1e12+5,0,0),App.Vector(1e12,5,0),App.Vector(1e12-5,0,0),App.Vector(1e12,-5,0)],[4,4],[0.,1.],False,3)
  owner=doc.addObject('Part::Feature','LocatedPoles');owner.Shape=c.toShape();owner.Placement.Base=App.Vector(-1e12,0,0);doc.recompute();Gui.Selection.clearSelection();Gui.Selection.addSelection(owner)
  enter('Circle');enter('FitPoints');enter('History=Yes');enter('Selection');enter('');child=doc.Objects[-1]
  check('Large local curve poles yield valid world fit',child.TypeId=='OpenMatrix9Gui::CircleHistory'and not child.Shape.isNull()and abs(child.Shape.Edges[0].Curve.Radius-5)<1e-7)
  report['poles_initial']=json.loads(child.OM9GeometryResult);child.touch();doc.recompute()
  check('Curve History respects local versus world limits',not child.Shape.isNull()and bool(child.OM9GeometryResult))
  if child.OM9GeometryResult:report['poles_replay']=json.loads(child.OM9GeometryResult)
  report['ok']=all(c['passed']for c in report['checks'])
 except Exception:report['ok']=False;report['error']=traceback.format_exc()
 finally:
  (out/'results.json').write_text(json.dumps(report,indent=2),encoding='utf-8')
  for name in list(App.listDocuments()):App.closeDocument(name)
  QtCore.QTimer.singleShot(100,Gui.getMainWindow().close)
QtCore.QTimer.singleShot(1000,run)
