"""RCORE-01: group publication and output frames cannot admit callback edits."""
import os,json,traceback,math
from pathlib import Path
import FreeCAD as App,FreeCADGui as Gui,Part,OpenMatrix9Gui as OM
from PySide6 import QtCore,QtGui,QtWidgets
out=Path(os.environ['OM9_SMOKE_OUTPUT']);report={'module':OM.__file__,'checks':[]}
def check(name,value):report['checks'].append(dict(name=name,passed=bool(value)))
def events():QtWidgets.QApplication.processEvents()
def enter(text=''):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier));events()
class Observer:
 fired=False;applied=False
 def slotChangedObject(self,obj,key):
  if obj.Document.Name!=self.doc.Name or self.fired:return
  if self.mode=='group' and obj.Name=='Owner' and key=='Group' and any(o.Name.startswith('Explode') for o in obj.Group):
   self.fired=True;obj.Group=[o for o in obj.Group if o.Name!='Sibling'];self.applied=not any(o.Name=='Sibling' for o in obj.Group)
  if self.mode=='nan' and obj.Name.startswith('Explode') and key=='OM9GeometryResult':
   self.fired=True;obj.Placement=App.Placement(App.Vector(float('nan'),0,0),App.Rotation());self.applied=math.isnan(obj.Placement.Base.x)
def run():
 global console
 observer=None
 try:
  Gui.activateWorkbench('OpenMatrix9Workbench');events();console=Gui.getMainWindow().findChild(QtWidgets.QPlainTextEdit,'OM9CommandTranscript')
  for mode in ['group','nan']:
   d=App.newDocument('EditMutation_'+mode);d.UndoMode=1;owner=d.addObject('App::Part','Owner')
   source=d.addObject('Part::Feature','Source');source.Shape=Part.Wire([Part.makeLine(App.Vector(),App.Vector(5,0,0)),Part.makeLine(App.Vector(5,0,0),App.Vector(5,3,0))]);owner.addObject(source)
   sibling=d.addObject('Part::Feature','Sibling');sibling.Shape=Part.makeBox(1,1,1);owner.addObject(sibling);d.recompute()
   baseline=(tuple(o.Name for o in d.Objects),source.Shape.exportBrepToString(),tuple(o.Name for o in owner.Group),d.UndoCount)
   Gui.Selection.clearSelection();Gui.Selection.addSelection(source);enter('Explode');enter()
   observer=Observer();observer.doc=d;observer.mode=mode;App.addDocumentObserver(observer)
   dialog=next(q for q in Gui.getMainWindow().findChildren(QtWidgets.QDialog,'OM9EditOptions') if q.isVisible());dialog.findChild(QtWidgets.QDialogButtonBox).button(QtWidgets.QDialogButtonBox.Ok).click();events();App.removeDocumentObserver(observer)
   check(mode+' callback mutation reaches the native document',observer.fired and observer.applied)
   check(mode+' callback mutation rejects all staged outputs',not any(getattr(o,'OM9FeatureId','')=='OM9-TOP11-005' for o in d.Objects))
   current=None
   if d.getObject('Source') and d.getObject('Owner'):current=(tuple(o.Name for o in d.Objects),d.getObject('Source').Shape.exportBrepToString(),tuple(o.Name for o in d.getObject('Owner').Group),d.UndoCount)
   report[mode+'_rollback']={'before_objects':baseline[0],'after_objects':current[0] if current else None,'before_members':baseline[2],'after_members':current[2] if current else None,'before_undo':baseline[3],'after_undo':d.UndoCount,'geometry_restored':current is not None and current[1]==baseline[1]}
   check(mode+' rollback restores source sibling membership and Undo',current==baseline)
   check(mode+' typed failure names affected publication','StaleGeometry' in console.toPlainText() and ('Owner' in console.toPlainText() if mode=='group' else 'frame' in console.toPlainText().lower()))
   enter('Cancel');App.closeDocument(d.Name)
  report['ok']=all(c['passed'] for c in report['checks'])
 except Exception:report['ok']=False;report['error']=traceback.format_exc()
 finally:
  if observer:
   try:App.removeDocumentObserver(observer)
   except Exception:pass
  for n in list(App.listDocuments()):App.closeDocument(n)
  (out/'results.json').write_text(json.dumps(report,indent=2),encoding='utf-8');QtCore.QTimer.singleShot(100,Gui.getMainWindow().close)
QtCore.QTimer.singleShot(1200,run)
