"""Actual native document callbacks may invalidate staged Edit input evidence."""
import os,json,traceback
from pathlib import Path
import FreeCAD as App,FreeCADGui as Gui,Part,OpenMatrix9Gui as OM
from PySide6 import QtCore,QtGui,QtWidgets
out=Path(os.environ['OM9_SMOKE_OUTPUT']);report={'module':OM.__file__,'checks':[]}
def check(name,value):report['checks'].append(dict(name=name,passed=bool(value)))
def events():QtWidgets.QApplication.processEvents()
def enter(text=''):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier));events()
class Observer:
 fired=False
 def slotCreatedObject(self,obj):
  if obj.Document.Name==self.doc.Name and obj.Name.startswith('Join') and not self.fired:
   self.fired=True;self.source.Shape=Part.makeLine(App.Vector(0,0,0),App.Vector(30,0,0))
def run():
 global console
 observer=None
 try:
  Gui.activateWorkbench('OpenMatrix9Workbench');events();console=Gui.getMainWindow().findChild(QtWidgets.QPlainTextEdit,'OM9CommandTranscript')
  d=App.newDocument('EditResultCallback');d.UndoMode=1
  a=d.addObject('Part::Feature','A');a.Shape=Part.makeLine(App.Vector(0,0,0),App.Vector(5,0,0))
  b=d.addObject('Part::Feature','B');b.Shape=Part.makeLine(App.Vector(5,0,0),App.Vector(10,0,0));d.recompute()
  d.openTransaction('Redo witness');a.Label='Redo witness';d.commitTransaction();d.undo();d.recompute()
  baseline=(tuple(o.Name for o in d.Objects),d.UndoCount,d.RedoCount,a.Shape.exportBrepToString(),b.Shape.exportBrepToString())
  Gui.Selection.clearSelection();Gui.Selection.addSelection(a);Gui.Selection.addSelection(b);enter('Join');enter()
  dialog=next(q for q in Gui.getMainWindow().findChildren(QtWidgets.QDialog,'OM9EditOptions') if q.isVisible())
  observer=Observer();observer.doc=d;observer.source=a;App.addDocumentObserver(observer)
  dialog.findChild(QtWidgets.QDialogButtonBox).button(QtWidgets.QDialogButtonBox.Ok).click();events();App.removeDocumentObserver(observer)
  check('actual output creation callback mutates the selected source',observer.fired)
  outputs=[o for o in d.Objects if getattr(o,'OM9FeatureId','')=='OM9-TOP11-008']
  check('source invalidation during publication rejects staged output',not outputs)
  current=None
  if d.getObject('A') and d.getObject('B'):current=(tuple(o.Name for o in d.Objects),d.UndoCount,d.RedoCount,d.getObject('A').Shape.exportBrepToString(),d.getObject('B').Shape.exportBrepToString())
  report['rollback_observation']={'before_objects':baseline[0],'after_objects':current[0] if current else None,'before_undo':baseline[1],'after_undo':d.UndoCount,'before_redo':baseline[2],'after_redo':d.RedoCount,'source_geometry_restored':current is not None and current[3:]==baseline[3:]}
  check('publication failure aborts geometry objects and Undo/Redo',current==baseline)
  check('publication failure names the stale source','A' in console.toPlainText() and ('changed' in console.toPlainText().lower() or 'stale' in console.toPlainText().lower()))
  enter('Cancel');d.redo();check('publication failure keeps executable Redo',d.getObject('A') is not None and d.getObject('A').Label=='Redo witness')
  report['ok']=all(c['passed'] for c in report['checks'])
 except Exception:report['ok']=False;report['error']=traceback.format_exc()
 finally:
  if observer:
   try:App.removeDocumentObserver(observer)
   except Exception:pass
  for n in list(App.listDocuments()):App.closeDocument(n)
  (out/'results.json').write_text(json.dumps(report,indent=2),encoding='utf-8');QtCore.QTimer.singleShot(100,Gui.getMainWindow().close)
QtCore.QTimer.singleShot(1200,run)
