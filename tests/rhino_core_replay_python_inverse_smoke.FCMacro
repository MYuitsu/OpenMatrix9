# SPDX-License-Identifier: LGPL-2.1-or-later
"""Private replay inverse keeps opaque Python identity through every retirement phase."""
import json,os,sys,traceback
from pathlib import Path
import FreeCAD as App,FreeCADGui as Gui,OpenMatrix9Gui as OM
from PySide6 import QtCore
out=Path(os.environ['OM9_SMOKE_OUTPUT']);report=dict(module=OM.__file__,checks=[],observations=[])
sys.path.insert(0,os.environ['OM9_REPLAY_RETIREMENT_PROBE']);import OM9ReplayRetirement as probe
class Opaque:
 saved=0
 def __getstate__(self):
  Opaque.saved+=1
  raise RuntimeError('inverse must retain native Python identity')
def state(doc):return dict(booked=doc.getBookedTransactionID(),pending=doc.HasPendingTransaction,undo=list(doc.UndoNames),redo=list(doc.RedoNames))
def check(name,value):report['checks'].append(dict(name=name,passed=bool(value)))
def run():
 try:
  Gui.activateWorkbench('OpenMatrix9Workbench')
  for phase in ['recovery','original','save']:
   for undo_mode in [0,1]:
    for booking in ['plain','booked','active','preserving']:
     key=f'{phase}/{undo_mode}/{booking}';doc=App.newDocument('PythonInverse');doc.UndoMode=undo_mode
     child=doc.getObject(probe.create(doc.Name));child.addProperty('App::PropertyPythonObject','Payload')
     original=Opaque();publication=Opaque();child.Payload=original;doc.recompute();doc.clearUndos()
     if undo_mode:doc.openTransaction('Prior redo');child.Output='prior-redo';doc.commitTransaction();doc.undo()
     if booking=='preserving':doc.openTransactionPreservingRedo('Caller')
     elif booking!='plain':doc.openTransaction('Caller')
     if booking=='active':child.Value='caller-value'
     before=state(doc);value=child.Value;saved=Opaque.saved
     (out/'test-started.json').write_text(json.dumps(dict(case=key,before=before)))
     result=probe.run(doc.Name,'value',phase,publication)
     check(key+' actual native retirement callback',result['callbacks']==1)
     check(key+' mutation rejected by typed replay barrier',result['blocked']==1 and 'StaleGeometry'in result['blocked_error'])
     check(key+' completed native rollback and paired cleanup',not result['accepted']and result['rollback']and result['complete'])
     check(key+' original native owner and child retained',doc.Name in App.listDocuments()and doc.getObject('Child')is child)
     check(key+' original Python identity restored',child.Payload is original)
     check(key+' private values restored and paired output cleared',child.Value==value and child.Output=='')
     check(key+' original caller and history preserved',state(doc)==before)
     check(key+' no Python serialization',Opaque.saved==saved)
     if booking!='plain':doc.abortTransaction()
     if before['redo']:doc.redo();check(key+' prior Redo remains executable',child.Output=='prior-redo')
     report['observations'].append(dict(case=key,result=result,serialization_calls=Opaque.saved-saved))
     (out/'partial-results.json').write_text(json.dumps(report,indent=2))
     App.closeDocument(doc.Name)
  report['ok']=all(c['passed']for c in report['checks'])
 except Exception:report['ok']=False;report['error']=traceback.format_exc()
 finally:
  (out/'results.json').write_text(json.dumps(report,indent=2))
  for name in list(App.listDocuments()):App.closeDocument(name)
  QtCore.QTimer.singleShot(100,Gui.getMainWindow().close)
QtCore.QTimer.singleShot(1000,run)
