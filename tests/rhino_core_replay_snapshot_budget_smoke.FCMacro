# SPDX-License-Identifier: LGPL-2.1-or-later
"""Bound native history/name snapshots before copying, retaining executable history."""
import json, os, sys, traceback
from pathlib import Path
import FreeCAD as App, FreeCADGui as Gui
from PySide6 import QtCore
out = Path(os.environ['OM9_SMOKE_OUTPUT'])
report = dict(checks=[], observations=[])

def check(name, value):
    report['checks'].append(dict(name=name, passed=bool(value)))

def state(doc):
    return (doc.getBookedTransactionID(), doc.HasPendingTransaction,
            list(doc.UndoNames), list(doc.RedoNames))

def run():
    try:
        Gui.activateWorkbench('OpenMatrix9Workbench')
        import OpenMatrix9Gui as OM
        report['module'] = OM.__file__
        sys.path.insert(0, os.environ['OM9_REPLAY_SCOPE_PROBE'])
        import OM9ReplayScope as probe
        report['probe'] = probe.__file__
        for preserving in [False, True]:
            for records, capture, expected in [(3, False, False), (4, False, True),
                                               (4, True, False), (5, True, True)]:
                key = f'history/{preserving}/{records}/{capture}'
                doc = App.newDocument('SnapshotHistory')
                doc.UndoMode = 1
                child = doc.addObject('App::FeaturePython', 'Child')
                child.Label = 'original'
                doc.clearUndos()
                for i in range(4):
                    doc.openTransaction('History ' + str(i))
                    child.Label = 'history-' + str(i)
                    doc.commitTransaction()
                doc.undo(); doc.undo()
                if preserving:
                    doc.openTransactionPreservingRedo('Caller')
                    child.Label = 'caller-first-write'
                before = state(doc); label = child.Label
                result = probe.budget(doc.Name, child.Name, records, 65536, capture)
                check(key + ' enforces aggregate history and property record cap',
                      result['verified'] == expected and
                      (expected or 'InvalidBasis' in result['error']))
                check(key + ' leaves exact caller and original property unchanged',
                      state(doc) == before and child.Label == label and
                      doc.getObject('Child') is child)
                followup = probe.budget(doc.Name, child.Name, 5, 65536, True)
                check(key + ' constructor/capture rejection leaves scope reusable',
                      followup['verified'] and followup['restored'] and
                      state(doc) == before and child.Label == label)
                if preserving:
                    doc.abortTransaction()
                doc.redo(); doc.redo()
                check(key + ' original native Redo remains executable', child.Label == 'history-3')
                report['observations'].append(dict(case=key, result=result, followup=followup))
                App.closeDocument(doc.Name)
        for active in [False, True]:
            doc = App.newDocument('SnapshotNames')
            doc.UndoMode = 1
            child = doc.addObject('App::FeaturePython', 'Child')
            child.Label = 'original'; doc.clearUndos()
            doc.openTransaction('N' * 8192)
            if active:
                child.Label = 'caller-first-write'
            before = state(doc); label = child.Label
            result = probe.budget(doc.Name, child.Name, 10, 2048, False)
            check(f'name/{active} rejects description before oversized snapshot copy',
                  not result['entered'] and 'InvalidBasis' in result['error'])
            check(f'name/{active} preserves native booking and ownership',
                  state(doc) == before and child.Label == label and doc.getObject('Child') is child)
            followup = probe.budget(doc.Name, child.Name, 10, 65536, True)
            check(f'name/{active} permits a sufficient memory budget afterward',
                  followup['verified'] and followup['restored'] and state(doc) == before and child.Label == label)
            report['observations'].append(dict(case=f'name/{active}', result=result, followup=followup))
            doc.abortTransaction(); App.closeDocument(doc.Name)
        report['ok'] = all(c['passed'] for c in report['checks'])
    except Exception:
        report['ok'] = False; report['error'] = traceback.format_exc()
    finally:
        (out / 'results.json').write_text(json.dumps(report, indent=2))
        for name in list(App.listDocuments()):
            App.closeDocument(name)
        QtCore.QTimer.singleShot(100, Gui.getMainWindow().close)
QtCore.QTimer.singleShot(1000, run)
