"""Native callbacks must not replace a staged Edit Shape or its result."""
import os,json,traceback
from pathlib import Path
import FreeCAD as App,FreeCADGui as Gui,Part,OpenMatrix9Gui as OM
from PySide6 import QtCore,QtGui,QtWidgets
out=Path(os.environ['OM9_SMOKE_OUTPUT']);report={'module':OM.__file__,'checks':[]}
def check(name,value):report['checks'].append(dict(name=name,passed=bool(value)))
def events():QtWidgets.QApplication.processEvents()
def enter(text=''):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier));events()
class Observer:
 fired=False
 def slotChangedObject(self,obj,key):
  if obj.Document.Name==self.doc.Name and obj.Name.startswith('Join') and key=='OM9GeometryResult' and not self.fired:
   self.fired=True
   if self.mode=='shape':obj.Shape=Part.makeLine(App.Vector(),App.Vector(60,0,0))
   else:obj.OM9GeometryResult='{}'
def run():
 global console
 observer=None
 try:
  Gui.activateWorkbench('OpenMatrix9Workbench');events();console=Gui.getMainWindow().findChild(QtWidgets.QPlainTextEdit,'OM9CommandTranscript')
  for mode in ['shape','result']:
   d=App.newDocument('EditOutputCallback_'+mode);d.UndoMode=1
   a=d.addObject('Part::Feature','A');a.Shape=Part.makeLine(App.Vector(),App.Vector(5,0,0))
   b=d.addObject('Part::Feature','B');b.Shape=Part.makeLine(App.Vector(5,0,0),App.Vector(10,0,0));d.recompute()
   baseline=(tuple(o.Name for o in d.Objects),a.Shape.exportBrepToString(),b.Shape.exportBrepToString(),d.UndoCount)
   Gui.Selection.clearSelection();Gui.Selection.addSelection(a);Gui.Selection.addSelection(b);enter('Join');enter()
   observer=Observer();observer.doc=d;observer.mode=mode;App.addDocumentObserver(observer)
   dialog=next(q for q in Gui.getMainWindow().findChildren(QtWidgets.QDialog,'OM9EditOptions') if q.isVisible())
   dialog.findChild(QtWidgets.QDialogButtonBox).button(QtWidgets.QDialogButtonBox.Ok).click();events();App.removeDocumentObserver(observer)
   check(mode+' callback actually changes staged output',observer.fired)
   check(mode+' mismatch rejects every output',not any(getattr(o,'OM9FeatureId','')=='OM9-TOP11-008' for o in d.Objects))
   current=None
   if d.getObject('A') and d.getObject('B'):current=(tuple(o.Name for o in d.Objects),d.getObject('A').Shape.exportBrepToString(),d.getObject('B').Shape.exportBrepToString(),d.UndoCount)
   check(mode+' failed publication restores sources and Undo',current==baseline)
   check(mode+' failure identifies Edit output','StaleGeometry' in console.toPlainText() and 'Join' in console.toPlainText())
   enter('Cancel');App.closeDocument(d.Name)
  report['ok']=all(c['passed'] for c in report['checks'])
 except Exception:report['ok']=False;report['error']=traceback.format_exc()
 finally:
  if observer:
   try:App.removeDocumentObserver(observer)
   except Exception:pass
  for n in list(App.listDocuments()):App.closeDocument(n)
  (out/'results.json').write_text(json.dumps(report,indent=2),encoding='utf-8');QtCore.QTimer.singleShot(100,Gui.getMainWindow().close)
QtCore.QTimer.singleShot(1200,run)
