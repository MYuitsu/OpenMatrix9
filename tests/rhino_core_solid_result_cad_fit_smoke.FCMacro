"""A single selected CAD vertex keeps the complete owned native source master."""
import json,math,os,traceback
from pathlib import Path
import FreeCAD as App,FreeCADGui as Gui,Part,OpenMatrix9Gui as OM
from PySide6 import QtCore,QtGui,QtWidgets
out=Path(os.environ['OM9_SMOKE_OUTPUT']);report=dict(module=OM.__file__,checks=[],observations=[])
def check(name,value):report['checks'].append(dict(name=name,passed=bool(value)))
def enter(console,text):
    console.setFocus()
    QtWidgets.QApplication.sendEvent(console,QtGui.QKeyEvent(QtCore.QEvent.KeyPress,QtCore.Qt.Key_End,QtCore.Qt.ControlModifier))
    if text:QtWidgets.QApplication.sendEvent(console,QtGui.QKeyEvent(QtCore.QEvent.KeyPress,0,QtCore.Qt.NoModifier,text))
    QtWidgets.QApplication.sendEvent(console,QtGui.QKeyEvent(QtCore.QEvent.KeyPress,QtCore.Qt.Key_Return,QtCore.Qt.NoModifier));QtWidgets.QApplication.processEvents()
def run():
    doc=None
    try:
        Gui.activateWorkbench('OpenMatrix9Workbench');console=Gui.getMainWindow().findChild(QtWidgets.QPlainTextEdit,'OM9CommandTranscript')
        doc=App.newDocument('SolidResultCadFit');doc.UndoMode=1;OM.setUnitContext(doc.Name,1.,1.,.01,.001,.01)
        source=doc.addObject('Part::Feature','Source');source.Shape=Part.makeCompound([Part.Vertex(App.Vector(math.cos(i*.01),math.sin(i*.01),0)) for i in range(1000)])
        doc.recompute();before=doc.UndoCount
        for text in ['Sphere','FitPoints','0,1,0','-1,0,0']:enter(console,text)
        Gui.Selection.clearSelection();Gui.Selection.addSelection(source,'Vertex1');enter(console,'Selection');Gui.Selection.clearSelection();enter(console,'')
        obj=doc.getObject('Sphere');value=json.loads(getattr(obj,'OM9GeometryResult','{}')) if obj else {}
        refs=value.get('operation_context',{}).get('source_refs',[]);inputs=value.get('input_snapshots',[])
        check('selected native CAD vertex creates valid independent sphere',obj is not None and obj.Shape.isValid() and abs(obj.Shape.Volume-4*math.pi/3)<1e-7)
        check('selected subelement is bound to owned full CAD source',len(refs)==1 and refs[0]['subelement']=='Vertex1' and len(inputs)==2 and inputs[1]['native_shape_type']==0)
        master=Part.Shape()
        if len(inputs)==2:master.importBrepFromString(inputs[1]['geometry_data']['native_master']['payload'])
        check('source master retains all 1000 native vertices',len(master.Vertexes)==1000 and len(source.Shape.Vertexes)==1000)
        check('numeric and selected source ranges match independent inputs',bool(value) and value['operation_context']['construction']['accepted_points']==[[0,1,0],[-1,0,0],[1,0,0]] and refs[0]['point_begin']==2 and refs[0]['point_end']==3)
        check('CAD result is one native Undo with unchanged source',obj is not None and doc.UndoCount==before+1 and len(source.Shape.Vertexes)==1000)
        report['observations'].append(dict(result=value,diagnostic=console.toPlainText()));report['ok']=all(c['passed'] for c in report['checks'])
    except Exception:report['ok']=False;report['error']=traceback.format_exc()
    finally:
        Gui.Selection.clearSelection()
        if doc:App.closeDocument(doc.Name)
        (out/'results.json').write_text(json.dumps(report,indent=2),encoding='utf-8');QtCore.QTimer.singleShot(100,Gui.getMainWindow().close)
QtCore.QTimer.singleShot(1200,run)
