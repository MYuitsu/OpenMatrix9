"""Second-process FCStd restore from owned mesh/cloud result data."""
import json,os,sys,traceback
from pathlib import Path
import FreeCAD as App,FreeCADGui as Gui,Mesh
from PySide6 import QtCore
sys.path.insert(0,os.environ['OM9_TEST_NATIVE_DIR'])
out=Path(os.environ['OM9_SMOKE_OUTPUT']);report={'checks':[]}
def check(name,value):report['checks'].append(dict(name=name,passed=bool(value)))
def run():
 try:
  import OpenMatrix9Gui as native,ThreeDmPointCloud
  report['module']=native.__file__;Gui.activateWorkbench('OpenMatrix9Workbench')
  source=Path(os.environ['OM9_PREPARED_DISCRETE_RESULTS']);warm=json.loads(source.read_text());report['source_results']=str(source)
  doc=App.openDocument(warm['saved_file'])
  for name,expected in warm['saved_reports'].items():
   obj=doc.getObject(name);raw=getattr(obj,'OM9GeometryResult',None);result=json.loads(raw) if raw else {}
   check(name+' cold report bytes preserved',raw==warm['saved_report_bytes'][name])
   check(name+' cold immutable result preserved',result==expected and result.get('lifetime')=='immutable_import_evidence_not_current_validity')
   data=result['output_snapshots'][0]['geometry_data'];kind=data['representation']
   check(name+' remains discrete without CAD master',kind in ('mesh','point_cloud') and 'native_master' not in data)
   if kind=='mesh':
    reconstructed=Mesh.Mesh([[App.Vector(*data['points_xyz'][index]) for index in triangle] for triangle in data['triangles']])
    matrix=App.Matrix();matrix.A=[number for row in data['native_discrete_location'] for number in row];reconstructed.transform(matrix)
    matches=reconstructed.Topology==obj.Mesh.Topology
   else:matches=ThreeDmPointCloud.fields(obj)==data['current_fields']==warm['expected_cloud']
   check(name+' independently owned current data matches cold host',matches)
  report['ok']=all(c['passed'] for c in report['checks'])
 except Exception:report['ok']=False;report['error']=traceback.format_exc()
 finally:
  (out/'results.json').write_text(json.dumps(report,indent=2))
  for name in list(App.listDocuments()):App.closeDocument(name)
  Gui.getMainWindow().close()
QtCore.QTimer.singleShot(1200,run)
