# OM9-SNAP-002: initial native endpoint snap evidence, not full topology coverage.
import os,json,traceback
from pathlib import Path
import sys
sys.path.insert(0,str(Path(__file__).parent))
from command_console_support import command_input,command_prompt
import FreeCAD as App,FreeCADGui as Gui,Part
from PySide6 import QtCore,QtGui,QtWidgets,QtTest
from pivy import coin
out=Path(os.environ['OM9_SMOKE_OUTPUT']);result={'checks':[]}
def check(name,ok):
    result['checks'].append({'name':name,'passed':bool(ok)})
    if not ok:raise AssertionError(name)
def settle():
    loop=QtCore.QEventLoop();QtCore.QTimer.singleShot(350,loop.quit);loop.exec();QtCore.QCoreApplication.sendPostedEvents(None,QtCore.QEvent.DeferredDelete)
def cmd(text):
    field.setText(text);QtTest.QTest.keyClick(field,QtCore.Qt.Key_Return);settle()
def run():
    global field
    try:
        Gui.activateWorkbench('OpenMatrix9Workbench');doc=App.newDocument('EndSnapTest');doc.UndoMode=1;settle()
        line=doc.addObject('Part::Feature','Guide');line.Shape=Part.makeLine(App.Vector(0,0,10),App.Vector(10,0,10));doc.recompute();settle()
        window=Gui.getMainWindow();window.show();window.resize(1500,1000);settle();field=command_input(window);prompt=command_prompt(window);action=window.findChild(QtGui.QAction,'Osnap E')
        check('OM9-SNAP-002 original End Snap command is checkable',action is not None and action.isEnabled() and action.isCheckable())
        cmd('Osnap E');settle()
        result['end_mode_after_cmd']={'saved_state':App.ParamGet('User parameter:BaseApp/Preferences/Mod/OpenMatrix9/Osnap').GetInt('State',-1),'checked':action.isChecked(),'prompt':prompt.text()}
        check('CMD turns End Snap mode on',action.isChecked());cmd('Osnap On')
        master=window.findChild(QtWidgets.QToolButton,'OM9OsnapMaster')
        check('CMD synchronizes main O-Snap switch',master is not None and master.isChecked())
        master.click();settle();check('mouse master switch preserves End mode',not master.isChecked() and action.isChecked())
        master.click();settle();check('mouse master switch restores O-Snap',master.isChecked())
        Gui.activateWorkbench('PartWorkbench');settle()
        Gui.activateWorkbench('OpenMatrix9Workbench');settle()
        check('workbench reactivation restores independent snap choices',master.isChecked() and action.isChecked())
        check('snap choices are persisted in native preferences',App.ParamGet('User parameter:BaseApp/Preferences/Mod/OpenMatrix9/Osnap').GetInt('State',-1)==3)
        area=window.findChild(QtWidgets.QMdiArea);sub=next(s for s in area.subWindowList() if s.widget().property('om9ViewSlot')==0);area.setActiveSubWindow(sub);settle()
        viewer=next(w for w in sub.widget().findChildren(QtWidgets.QWidget) if w.metaObject().className()=='Gui::View3DInventorViewer').viewport();nearEnd=viewer.rect().center()+QtCore.QPoint(3,2)
        cmd('Distance');cmd('0,0,0');QtTest.QTest.mouseClick(viewer,QtCore.Qt.LeftButton,pos=nearEnd);settle()
        check('native mouse uses exact endpoint outside C-plane',prompt.text()=='Distance: 10 mm')
        cmd('Angle');cmd('0,0,0');QtTest.QTest.mouseClick(viewer,QtCore.Qt.LeftButton,pos=nearEnd);settle();cmd('0,0,0');cmd('10,0,0')
        check('Angle mouse input uses spatial endpoint shared with Distance',prompt.text().startswith('Angle: 90'))
        mid_action=window.findChild(QtGui.QAction,'Osnap M')
        check('OM9-SNAP-003 original Mid command is checkable',mid_action is not None and mid_action.isCheckable())
        cmd('Osnap E');cmd('Osnap M');line.Shape=Part.makeLine(App.Vector(-10,0,10),App.Vector(10,0,10));doc.recompute();settle()
        cmd('Distance');cmd('0,0,0');QtTest.QTest.mouseClick(viewer,QtCore.Qt.LeftButton,pos=nearEnd);settle()
        check('Mid-only mouse snaps to exact spatial line midpoint',mid_action.isChecked() and not action.isChecked() and prompt.text()=='Distance: 10 mm')
        mid_button=window.findChild(QtWidgets.QToolButton,'OM9SnapMid');settle()
        check('Mid sidebar reflects CMD mode',mid_button is not None and mid_button.isEnabled() and mid_button.isCheckable() and mid_button.isChecked())
        result['mid_sidebar_before']={'visible':mid_button.isVisible(),'global':str(mid_button.mapToGlobal(mid_button.rect().center())),'screen':str(window.screen().availableGeometry()),'state':App.ParamGet('User parameter:BaseApp/Preferences/Mod/OpenMatrix9/Osnap').GetInt('State',-1),'buttons':len(window.findChildren(QtWidgets.QToolButton,'OM9SnapMid'))}
        mid_button.clicked.connect(lambda checked:result.setdefault('mid_clicks',[]).append(bool(checked)))
        class Trace(QtCore.QObject):
            def __init__(self,where):super().__init__();self.where=where
            def eventFilter(self,receiver,event):
                if receiver is mid_button and event.type() in (QtCore.QEvent.MouseButtonPress,QtCore.QEvent.MouseButtonRelease):result.setdefault('mid_events',[]).append({'where':self.where,'type':int(event.type()),'position':str(event.position()),'rect':str(mid_button.rect()),'enabled':mid_button.isEnabled(),'signals_blocked':mid_button.signalsBlocked(),'down':mid_button.isDown()})
                return False
        app_trace=Trace('app');button_trace=Trace('button');QtWidgets.QApplication.instance().installEventFilter(app_trace);mid_button.installEventFilter(button_trace)
        QtTest.QTest.mouseClick(mid_button,QtCore.Qt.LeftButton,pos=mid_button.rect().center());settle();result['mid_after']={'button':mid_button.isChecked(),'action':mid_action.isChecked(),'state':App.ParamGet('User parameter:BaseApp/Preferences/Mod/OpenMatrix9/Osnap').GetInt('State',-1),'tooltip':mid_button.toolTip(),'property':str(mid_button.property('om9Command'))};check('Mid sidebar mouse disables shared mode',not mid_button.isChecked() and not mid_action.isChecked())
        QtTest.QTest.mouseClick(mid_button,QtCore.Qt.LeftButton,pos=mid_button.rect().center());settle();check('Mid sidebar mouse restores shared mode',mid_button.isChecked() and mid_action.isChecked())
        line.Shape=Part.makeCircle(10,App.Vector(0,-10,10),App.Vector(0,0,1),0,180);doc.recompute();settle()
        cmd('Distance');cmd('0,0,0');QtTest.QTest.mouseClick(viewer,QtCore.Qt.LeftButton,pos=nearEnd);settle()
        check('OM9-SNAP-003 curved midpoint follows half arc length',prompt.text().startswith('Distance: ') and abs(float(prompt.text().split()[1])-10)<1e-9)
        line.Shape=Part.makePlane(20,10,App.Vector(-10,0,10));doc.recompute();settle()
        cmd('Distance');cmd('0,0,0');QtTest.QTest.mouseClick(viewer,QtCore.Qt.LeftButton,pos=nearEnd);settle()
        check('OM9-SNAP-003 native surface edge midpoint is eligible',prompt.text()=='Distance: 10 mm')
        line.Shape=Part.makePlane(100,100,App.Vector(-50,-50,10));doc.recompute();settle()
        cmd('Distance');cmd('0,0,0');QtTest.QTest.mouseClick(viewer,QtCore.Qt.LeftButton,pos=nearEnd);settle()
        check('OM9-SNAP-003 surface interior midpoint is eligible',prompt.text()=='Distance: 10 mm')
        hole=Part.Face(Part.Wire(Part.makeCircle(20,App.Vector(0,0,10))));line.Shape=line.Shape.cut(hole);doc.recompute();settle()
        cmd('Distance');cmd('0,0,0');QtTest.QTest.mouseClick(viewer,QtCore.Qt.LeftButton,pos=nearEnd);settle()
        check('trimmed face hole excludes surface midpoint',prompt.text().startswith('Distance: ') and float(prompt.text().split()[1])<5)
        surface=Part.BSplineSurface()
        poles=[[App.Vector(x,y,-20 if x==0 and y==0 else 20) for y in (-20,0,20)] for x in (-20,0,20)]
        surface.buildFromPolesMultsKnots(poles,[3,3],[3,3],[0,1],[0,1],False,False,2,2)
        line.Shape=surface.toShape();doc.recompute();settle()
        native_center=surface.value(0.5,0.5)
        cmd('Distance');cmd('0,0,0');QtTest.QTest.mouseClick(viewer,QtCore.Qt.LeftButton,pos=nearEnd);settle()
        check('OM9-SNAP-003 curved surface midpoint matches native UV evaluation',(native_center-App.Vector(0,0,10)).Length<1e-9 and prompt.text().startswith('Distance: ') and abs(float(prompt.text().split()[1])-native_center.Length)<1e-9)
        mid_action.trigger();settle();check('Mid menu shares CMD state',not mid_action.isChecked())
        cmd('Osnap E');line.Shape=Part.makeLine(App.Vector(0,0,10),App.Vector(10,0,10));doc.recompute();settle()
        line.Placement.Base=App.Vector(0,0,10);doc.recompute();settle()
        cmd('Distance');cmd('0,0,0');QtTest.QTest.mouseClick(viewer,QtCore.Qt.LeftButton,pos=nearEnd);settle()
        check('object placement transforms endpoint into world coordinates',prompt.text()=='Distance: 20 mm')
        line.Placement=App.Placement();line.Shape=Part.makePolygon([App.Vector(-10,0,10),App.Vector(0,0,10),App.Vector(10,0,10)]);doc.recompute();settle()
        cmd('Distance');cmd('0,0,0');QtTest.QTest.mouseClick(viewer,QtCore.Qt.LeftButton,pos=nearEnd);settle()
        check('joined polyline interior vertex is an End candidate',prompt.text()=='Distance: 10 mm')
        line.Shape=Part.makeCircle(5,App.Vector(-5,0,10));doc.recompute();settle()
        cmd('Distance');cmd('0,0,0');QtTest.QTest.mouseClick(viewer,QtCore.Qt.LeftButton,pos=nearEnd);settle()
        check('closed circle seam is an End candidate',prompt.text()=='Distance: 10 mm')
        line.Shape=Part.makePlane(10,10,App.Vector(0,0,10));doc.recompute();settle()
        cmd('Distance');cmd('0,0,0');QtTest.QTest.mouseClick(viewer,QtCore.Qt.LeftButton,pos=nearEnd);settle()
        check('surface corner is an End candidate',prompt.text()=='Distance: 10 mm')
        line.Shape=Part.makeBox(10,10,2,App.Vector(0,0,10));doc.recompute();settle()
        cmd('Distance');cmd('0,0,0');QtTest.QTest.mouseClick(viewer,QtCore.Qt.LeftButton,pos=nearEnd);settle()
        check('polysurface topology corner is an End candidate',prompt.text() in ('Distance: 10 mm','Distance: 12 mm'))
        line.Shape=Part.makeLine(App.Vector(10,0,0),App.Vector(15,0,0));line.Placement=App.Placement(App.Vector(0,0,20),App.Rotation(App.Vector(0,1,0),90));doc.recompute();settle()
        cmd('Distance');cmd('0,0,0');QtTest.QTest.mouseClick(viewer,QtCore.Qt.LeftButton,pos=nearEnd);settle()
        rotated_distance=float(prompt.text().split()[1]) if prompt.text().startswith('Distance: ') else float('nan')
        check('rotated endpoint uses world placement',min(abs(rotated_distance-10),abs(rotated_distance-5))<1e-9)
        line.Placement=App.Placement();line.Shape=Part.makeLine(App.Vector(0,0,10),App.Vector(10,0,10));doc.recompute();settle()
        group=doc.addObject('App::Part','PlacedGroup');group.addObject(line);group.Placement.Base=App.Vector(0,0,20);doc.recompute();settle()
        cmd('Distance');cmd('0,0,0');QtTest.QTest.mouseClick(viewer,QtCore.Qt.LeftButton,pos=nearEnd);settle()
        check('nested group placement transforms endpoint',prompt.text()=='Distance: 30 mm')
        group.ViewObject.Visibility=False;settle()
        cmd('Distance');cmd('0,0,0');QtTest.QTest.mouseClick(viewer,QtCore.Qt.LeftButton,pos=nearEnd);settle()
        check('hidden parent excludes child endpoint',prompt.text().startswith('Distance: ') and float(prompt.text().split()[1])<5)
        group.ViewObject.Visibility=True;settle()
        group.removeObject(line);doc.removeObject(group.Name);doc.recompute();settle()
        link=doc.addObject('App::Link','LinkedGuide');link.setLink(line);link.LinkPlacement.Base=App.Vector(0,0,20);line.ViewObject.Visibility=False;doc.recompute();settle()
        cmd('Distance');cmd('0,0,0');QtTest.QTest.mouseClick(viewer,QtCore.Qt.LeftButton,pos=nearEnd);settle()
        result['link_diagnostics']={'prompt':prompt.text(),'vertices':[list(v.Point) for v in link.getSubObject('').Vertexes],'source_vertices':[list(v.Point) for v in line.Shape.Vertexes]}
        check('visible link snaps at instance placement with hidden source',prompt.text()=='Distance: 30 mm')
        link.ViewObject.Visibility=False;settle()
        cmd('Distance');cmd('0,0,0');QtTest.QTest.mouseClick(viewer,QtCore.Qt.LeftButton,pos=nearEnd);settle()
        check('hidden link and hidden source supply no endpoint',prompt.text().startswith('Distance: ') and float(prompt.text().split()[1])<5)
        link.ViewObject.Visibility=True;link.Scale=2;doc.recompute();settle()
        native_endpoint=link.getSubObject('').Vertexes[0].Point
        cmd('Distance');cmd('0,0,0');QtTest.QTest.mouseClick(viewer,QtCore.Qt.LeftButton,pos=nearEnd);settle()
        measured=float(prompt.text().split()[1]) if prompt.text().startswith('Distance: ') else float('nan')
        check('scaled link snap matches native instance endpoint',native_endpoint.Length>10 and abs(measured-native_endpoint.Length)<1e-9)
        doc.removeObject(link.Name);line.ViewObject.Visibility=True;doc.recompute();settle()
        cmd('Osnap Off');settle();check('master off preserves End mode',action.isChecked())
        cmd('Distance');cmd('0,0,0');QtTest.QTest.mouseClick(viewer,QtCore.Qt.LeftButton,pos=nearEnd);settle()
        check('master off uses plane fallback',prompt.text().startswith('Distance: ') and float(prompt.text().split()[1])<5)
        cmd('Osnap On');line.ViewObject.Visibility=False;settle()
        cmd('Distance');cmd('0,0,0');QtTest.QTest.mouseClick(viewer,QtCore.Qt.LeftButton,pos=nearEnd);settle()
        check('hidden object cannot supply endpoint',prompt.text().startswith('Distance: ') and float(prompt.text().split()[1])<5)
        line.ViewObject.Visibility=True;settle()
        action.trigger();settle();check('menu toggles same End Snap state off',not action.isChecked())
        check('snapping and mode controls create no objects or Undo',len(doc.Objects)==1 and not doc.UndoNames and not doc.RedoNames and not Gui.Selection.getSelection())
        cmd('Osnap M');Gui.activateWorkbench('PartWorkbench');settle();Gui.activateWorkbench('OpenMatrix9Workbench');settle()
        check('Mid-only state restored after workbench reactivation',mid_action.isChecked() and not action.isChecked() and master.isChecked())
        check('Mid-only state saved independently for restart',App.ParamGet('User parameter:BaseApp/Preferences/Mod/OpenMatrix9/Osnap').GetInt('State',-1)==5)
        result['ok']=True
    except Exception:result['ok']=False;result['error']=traceback.format_exc()
    finally:
        (out/'results.json').write_text(json.dumps(result,indent=2),encoding='utf-8')
        for name in list(App.listDocuments()):App.closeDocument(name)
        QtCore.QTimer.singleShot(500,Gui.getMainWindow().close)
QtCore.QTimer.singleShot(1800,run)
