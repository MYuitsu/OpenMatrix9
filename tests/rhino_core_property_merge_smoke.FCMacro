# SPDX-License-Identifier: LGPL-2.1-or-later
"""Actual native Transaction/Property tests, separate from Document replay scope."""
import json,os,sys,traceback
from pathlib import Path
import FreeCAD as App,FreeCADGui as Gui
from PySide6 import QtCore
out=Path(os.environ['OM9_SMOKE_OUTPUT']);report=dict(checks=[])
def run():
 try:
  import OpenMatrix9Gui as OM;report['module']=OM.__file__
  sys.path.insert(0,os.environ['OM9_PROPERTY_MERGE_PROBE']);import OM9PropertyMerge as probe
  report['probe']=probe.__file__;doc=App.newDocument('PropertyMerge');doc.UndoMode=0
  report['checks']=probe.run(doc.Name);report['ok']=all(c['passed']for c in report['checks'])
 except Exception:report['ok']=False;report['error']=traceback.format_exc()
 finally:
  (out/'results.json').write_text(json.dumps(report,indent=2))
  for name in list(App.listDocuments()):App.closeDocument(name)
  QtCore.QTimer.singleShot(100,Gui.getMainWindow().close)
QtCore.QTimer.singleShot(1000,run)
