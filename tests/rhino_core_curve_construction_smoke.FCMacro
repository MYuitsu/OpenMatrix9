"""Actual existing Curve constructors must persist owned normalized input state."""
import json,math,os,traceback
from pathlib import Path
import FreeCAD as App,FreeCADGui as Gui,Part,OpenMatrix9Gui as OM
from PySide6 import QtCore,QtGui,QtWidgets
out=Path(os.environ['OM9_SMOKE_OUTPUT']);report=dict(module=OM.__file__,checks=[],observations=[])
def check(name,value):report['checks'].append(dict(name=name,passed=bool(value)))
def enter(console,text):
 console.setFocus()
 QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier));QtWidgets.QApplication.processEvents()
def run():
 try:
  Gui.activateWorkbench('OpenMatrix9Workbench');QtWidgets.QApplication.processEvents();console=Gui.getMainWindow().findChild(QtWidgets.QPlainTextEdit,'OM9CommandTranscript')
  cases=[('Line',['BothSides=Yes','0,0,0','10,0,0'],2,20.,'OM9-CURVE-002'),('Polyline',['0,0,0','3,0,0','3,4,0','Close'],3,12.,'OM9-CURVE-001'),('Rectangle',['0,0,0','4,3,0'],2,14.,'OM9-CURVE-004'),('Circle',['3Point','1,0,0','0,1,0','-1,0,0'],3,2*math.pi,'OM9-CURVE-005'),('Ellipse',['1,2,3','6,2,3','1,5,3'],3,None,'OM9-CURVE-006'),('InterpCrv',['Degree=1','0,0,0','3,0,0','3,4,0',''],3,7.,'OM9-CURVE-003')]
  for command,texts,count,length,fid in cases:
   doc=App.newDocument('CurveConstruction'+command);doc.UndoMode=1;OM.setUnitContext(doc.Name,1.,1.,.01,.001,.01);before=doc.UndoCount
   enter(console,command)
   for text in texts:enter(console,text)
   obj=doc.getObject(command);raw=getattr(obj,'OM9CurveConstruction','') if obj else '';value=json.loads(raw) if raw else {}
   geometry=obj is not None and obj.Shape.isValid() and not obj.Shape.isNull()
   if geometry:
    geometry=abs(obj.Shape.Length-length)<1e-7 if length is not None else isinstance(obj.Shape.Edges[0].Curve,Part.Ellipse) and abs(obj.Shape.Edges[0].Curve.MajorRadius-5)<1e-7 and abs(obj.Shape.Edges[0].Curve.MinorRadius-3)<1e-7
   check(command+' reuses valid native solver with independent geometry',geometry)
   check(command+' owns exact constructor identity and generation',bool(value) and value.get('operation')=='ConstructCurve' and value.get('command')==command and value.get('feature_id')==fid and int(value.get('generation','0'))>0)
   check(command+' normalized inputs retained independently of output outline',len(value.get('normalized_points',[]))==count and value.get('coordinates')=='document_world_mm' and value.get('input_role')=='normalized_session_state_not_complete_accepted_input_history')
   check(command+' output role distinguishes CAD plan from display sampling',value.get('output_points_role')==('display_outline_only' if command in ('Circle','Ellipse') else 'native_constructor_points'))
   check(command+' Shape and construction have one Undo',doc.UndoCount==before+1)
   doc.undo();missing=doc.getObject(command) is None;doc.redo();obj=doc.getObject(command)
   check(command+' Undo Redo restores immutable construction bytes',missing and obj is not None and bool(raw) and getattr(obj,'OM9CurveConstruction','')==raw)
   path=out/(command+'.FCStd');name=doc.Name;doc.saveAs(str(path));App.closeDocument(name);doc=App.openDocument(str(path));obj=doc.getObject(command)
   check(command+' FCStd restores identical constructor state',obj is not None and bool(raw) and getattr(obj,'OM9CurveConstruction','')==raw)
   report['observations'].append(dict(command=command,raw=raw,construction=value,diagnostic=console.toPlainText()))
   enter(console,'Cancel');App.closeDocument(doc.Name)
  report['ok']=all(c['passed'] for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
