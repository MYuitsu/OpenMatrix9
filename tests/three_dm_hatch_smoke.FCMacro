import FreeCAD as App, FreeCADGui as Gui
import json,os,tempfile,traceback
from pathlib import Path
from PySide6 import QtCore
out=Path(os.environ['OM9_SMOKE_OUTPUT']);result={'checks':[]}
def check(name,value):
    result['checks'].append(dict(name=name,passed=bool(value)))
    if not value:raise AssertionError(name)
def near(a,b):return len(a)==len(b) and all(abs(x-y)<1e-9 for x,y in zip(a,b))
def center(row):
    bounds=row['hatch']['bounds'];return [(bounds[i]+bounds[i+3])/2 for i in range(3)]
def run():
    try:
        Gui.activateWorkbench('OpenMatrix9Workbench')
        import ThreeDm,OpenMatrix9Gui as native
        for unit,scale in [('mm',1),('cm',10)]:
            source=Path(tempfile.gettempdir())/('om9-hatch-'+unit+'.3dm');original=source.read_bytes();external=out/(unit+'-source.3dm');external.write_bytes(original);doc=App.newDocument('Hatch'+unit);doc.UndoMode=1;roots=ThreeDm.import_file(str(external),doc,mode='preserve');hatch=next(o for o in roots if o.OM9SourceClass=='ON_Hatch');base=json.loads(hatch.OM9SourceRecord);patternId=next(r['source_uuid'] for r in json.loads(hatch.OM9ArchiveOwner.OM9ArchiveManifest)['components'] if r['class_name']=='ON_HatchPattern' and r.get('hatch_pattern',{}).get('lines'));target=out/(unit+'-hatch.3dm')
            check(unit+' retained hatch binds exact native facts and custom pattern dependency',patternId in base['dependencies'] and len(base['hatch']['loops'])==2 and base['hatch']['loops'][0]['class_name']=='ON_NurbsCurve' and hasattr(hatch,'OM9BlockMemberPlacement') and not hasattr(hatch,'Shape'))
            def export(objects):
                ThreeDm.export_file(str(target),objects);report=json.loads(native.inspect3dm(str(target)));row=next(r for r in report['records'] if r['class_name']=='ON_Hatch');pattern=next(r for r in report['components'] if r['class_name']=='ON_HatchPattern');return row,pattern
            row,pattern=export([hatch]);check(unit+' selected hatch retains full line pattern identity and exact fields',pattern['source_uuid']==patternId and patternId in row['dependencies'] and pattern['hatch_pattern']['lines'][0]['dashes']==[3.123456789012345,-1.234567890123456,0] and abs(row['hatch']['scale']-base['hatch']['scale']*scale)<1e-10)
            doc.openTransaction('Place hatch');hatch.OM9BlockMemberPlacement.Base=App.Vector(5,6,7);doc.recompute();doc.commitTransaction();row,_=export([hatch]);check(unit+' retained placement moves native plane once and preserves spacing',near(center(row),[10*scale+5,20*scale+6,30*scale+7]) and abs(row['hatch']['scale']-base['hatch']['scale']*scale)<1e-10)
            doc.undo();doc.recompute();row,_=export([hatch]);check(unit+' Undo restores native hatch placement',near(center(row),[10*scale,20*scale,30*scale]))
            doc.redo();doc.recompute();parent=doc.addObject('App::Part','HatchParent');parent.addObject(hatch);parent.Placement.Base=App.Vector(100,200,300);doc.recompute();row,_=export([hatch]);check(unit+' physical parent and hatch local placement compose once',near(center(row),[10*scale+105,20*scale+206,30*scale+307]))
            name=hatch.Name;saved=out/(unit+'.FCStd');doc.saveAs(str(saved));external.unlink();App.closeDocument(doc.Name);doc=App.openDocument(str(saved));hatch=doc.getObject(name);row,pattern=export([hatch]);check(unit+' included hatch pattern and placement persist after source deletion and FCStd',not external.exists() and near(center(row),[10*scale+105,20*scale+206,30*scale+307]) and pattern['source_uuid']==patternId)
            copied=doc.copyObject(hatch,False);copied.OM9BlockMemberPlacement.Base=App.Vector(1,2,3);doc.recompute();row,_=export([copied]);check(unit+' independent hatch source copy retains native pattern without ancestor placement',row['source_uuid']!=hatch.OM9SourceUUID and near(center(row),[10*scale+1,20*scale+2,30*scale+3]))
            check(unit+' original immutable hatch source bytes preserved',source.read_bytes()==original);App.closeDocument(doc.Name)
        result['ok']=True
    except Exception:result['ok']=False;result['error']=traceback.format_exc()
    (out/'results.json').write_text(json.dumps(result,indent=2))
    for name in list(App.listDocuments()):App.closeDocument(name)
    QtCore.QTimer.singleShot(100,Gui.getMainWindow().close)
QtCore.QTimer.singleShot(1000,run)
