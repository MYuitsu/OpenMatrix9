# SPDX-License-Identifier: LGPL-2.1-or-later
"""Cold independent CAD reconstruction for every recorded all-mode result."""
import json,os,traceback
from pathlib import Path
import FreeCAD as App,FreeCADGui as Gui,Part,OpenMatrix9Gui as OM
from PySide6 import QtCore,QtWidgets
out=Path(os.environ['OM9_SMOKE_OUTPUT']);directory=Path(os.environ['OM9_CIRCLE_MODES_ARCHIVES']);report=dict(module=OM.__file__,checks=[])
def check(name,value):report['checks'].append(dict(name=name,passed=bool(value)))
def paired(child):
 try:
  result=json.loads(child.OM9GeometryResult);snapshot=result['output_snapshots'][0];master=Part.Shape();master.importBrepFromString(snapshot['geometry_data']['native_master']['payload'])
  if master.isNull()or child.Shape.isNull()or not master.isValid()or not master.isClosed()or snapshot['unit_context_snapshot']!=child.OM9UnitContext:return False
  a,b=child.Shape.Edges[0],master.Edges[0]
  return type(a.Curve)==type(b.Curve)and abs(a.FirstParameter-b.FirstParameter)<1e-7 and abs(a.LastParameter-b.LastParameter)<1e-7 and all((a.valueAt(a.FirstParameter+f*(a.LastParameter-a.FirstParameter))-b.valueAt(b.FirstParameter+f*(b.LastParameter-b.FirstParameter))).Length<1e-7 for f in [0,.1,.25,.5,.75,.9,1])
 except (ValueError,KeyError,IndexError,TypeError):return False
def run():
 try:
  Gui.activateWorkbench('OpenMatrix9Workbench');records=json.loads((directory/'recorded-results.json').read_text());doc=App.openDocument(str(directory/'history_more.FCStd'));report['recorded_results']=len(records)
  for record in records:
   child=doc.getObject(record['name']);check(record['name']+' cold exact saved result bytes',child.Recorded and child.OM9GeometryResult==record['raw']);check(record['name']+' cold independent native master agrees',paired(child))
  doc.getObject('SourceGroup').Placement.Base=App.Vector(0,46,0);doc.recompute()
  for record in records:check(record['name']+' restored source replay stays paired',paired(doc.getObject(record['name'])))
  names=json.loads((directory/'results.json').read_text())['history_objects'];scalar=doc.getObject(names['scalar']);spline=doc.getObject(names['spline'])
  check('cold restored analytic source changes physical center',(scalar.Shape.Edges[0].Curve.Center-App.Vector(1,46,0)).Length<1e-7)
  plan=json.loads(spline.OM9GeometryResult)['operation_context']['resolved_plan'];check('cold restored deformable result resolves current source center',plan['center']==[1,46,0]and spline.Shape.isClosed())
  report['ok']=all(c['passed']for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
