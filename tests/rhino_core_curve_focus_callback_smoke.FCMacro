# SPDX-License-Identifier: LGPL-2.1-or-later
"""Callbacks on either auxiliary focus must roll back the whole Ellipse booking."""
import json,os,traceback
from pathlib import Path
import FreeCAD as App,FreeCADGui as Gui,Part,OpenMatrix9Gui as OM
from PySide6 import QtCore,QtGui,QtWidgets
out=Path(os.environ['OM9_SMOKE_OUTPUT']);report=dict(module=OM.__file__,checks=[],observations=[])
def check(name,value):report['checks'].append(dict(name=name,passed=bool(value)))
def enter(console,text):
 console.setFocus();QtWidgets.QApplication.sendEvent(console,QtGui.QKeyEvent(QtCore.QEvent.KeyPress,QtCore.Qt.Key_End,QtCore.Qt.ControlModifier))
 if text:QtWidgets.QApplication.sendEvent(console,QtGui.QKeyEvent(QtCore.QEvent.KeyPress,0,QtCore.Qt.NoModifier,text))
 QtWidgets.QApplication.sendEvent(console,QtGui.QKeyEvent(QtCore.QEvent.KeyPress,QtCore.Qt.Key_Return,QtCore.Qt.NoModifier))
def settle():
 loop=QtCore.QEventLoop();QtCore.QTimer.singleShot(80,loop.quit);loop.exec()
def snapshot(doc):
 return dict(objects=[dict(name=o.Name,label=o.Label,shape=o.Shape.exportBrepToString()if 'Shape'in o.PropertiesList else None,
  placement=list(o.Placement.toMatrix().A)if 'Placement'in o.PropertiesList else None,
  members=[m.Name for m in o.Group]if 'Group'in o.PropertiesList else None)for o in doc.Objects],undo=doc.UndoCount,redo=doc.RedoCount)
class Observer:
 def __init__(self,doc,target,action):self.doc=doc.Name;self.target=target;self.action=action;self.calls=0;self.armed=True;self.events=[]
 def slotChangedObject(self,obj,prop):
  if not self.armed or obj.Document.Name!=self.doc or obj.Name!=self.target or prop!='OM9GeometryResult'or not getattr(obj,prop,''):return
  self.armed=False;self.calls+=1;doc=App.getDocument(self.doc)
  if self.action in ['commit','abort','commit-reopen','abort-reopen']:
   try:
    if self.action.startswith('commit'):doc.commitTransaction()
    else:doc.abortTransaction()
    self.events.append('close returned')
   except Exception as error:self.events.append('close rejected: '+str(error))
   if self.action.endswith('-reopen'):
    try:doc.openTransaction('Callback separate booking');self.events.append('reopen returned')
    except Exception as error:self.events.append('reopen rejected: '+str(error))
   doc.getObject('Witness').Label='Callback outside retired journal'
   current=doc.getObject(self.target)
   if current:current.Shape=Part.Vertex(App.Vector(100,200,300))
  elif self.action=='shape':obj.Shape=Part.Vertex(App.Vector(100,200,300))
  elif self.action=='placement':obj.Placement.Base=App.Vector(50,60,70)
  elif self.action=='construction':obj.OM9CurveConstruction='tampered construction'
  elif self.action=='result':obj.OM9GeometryResult='tampered result'
  elif self.action=='units':obj.OM9UnitContext='tampered units'
  elif self.action=='role':obj.OM9Role='Focus99'
  elif self.action=='feature-id':obj.OM9FeatureId='OM9-CURVE-001'
  elif self.action=='parent':doc.getObject('Parent').addObject(obj)
  elif self.action=='main':doc.getObject('Ellipse').Shape=Part.makeLine(App.Vector(),App.Vector(7,0,0))
def case(console,target,action):
 label=target+'/'+action;doc=App.newDocument('FocusCallback');observer=None
 try:
  doc.UndoMode=1;OM.setUnitContext(doc.Name,1.,1.,.01,.001,.01);witness=doc.addObject('App::FeaturePython','Witness')
  if action=='parent':parent=doc.addObject('App::Part','Parent');parent.Placement.Base=App.Vector(20,30,40)
  doc.recompute();doc.openTransaction('Prior executable Redo');witness.Label='Prior Redo executes';doc.commitTransaction();doc.undo();settle()
  console.clear()
  for text in ['Ellipse','FromFoci','MarkFoci=Yes','-4,0,0','4,0,0']:enter(console,text)
  before=snapshot(doc);observer=Observer(doc,target,action);App.addDocumentObserver(observer);enter(console,'0,3,0');settle()
  calls=observer.calls;events=observer.events;App.removeDocumentObserver(observer);observer=None;after=snapshot(doc);diagnostic=console.toPlainText()
  check(label+' target focus callback once',calls==1)
  check(label+' entire document Undo and prior Redo restored',before==after and before['redo']==1)
  check(label+' no main or auxiliary output remains',all(doc.getObject(name)is None for name in ['Ellipse','EllipseFocus1','EllipseFocus2']))
  check(label+' typed actual Ellipse diagnostic',any('StaleGeometry:'in line and 'Ellipse'in line for line in diagnostic.splitlines()))
  executed=False
  if doc.RedoCount:doc.redo();executed=witness.Label=='Prior Redo executes'
  check(label+' original native Redo executes',executed)
  report['observations'].append(dict(case=label,before=before,after=after,calls=calls,events=events,diagnostic=diagnostic))
 finally:
  if observer:App.removeDocumentObserver(observer)
  enter(console,'Cancel');App.closeDocument(doc.Name)
def run():
 try:
  Gui.activateWorkbench('OpenMatrix9Workbench');settle();console=Gui.getMainWindow().findChild(QtWidgets.QPlainTextEdit,'OM9CommandTranscript')
  for target in ['EllipseFocus1','EllipseFocus2']:
   for action in ['shape','placement','construction','result','units','role','feature-id','parent','main','commit','abort','commit-reopen','abort-reopen']:case(console,target,action)
  report['ok']=all(c['passed']for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
