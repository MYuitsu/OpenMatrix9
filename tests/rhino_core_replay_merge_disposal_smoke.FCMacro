# SPDX-License-Identifier: LGPL-2.1-or-later
"""An open-notification exception retires merge snapshots inside the barrier."""
import json,os,sys,traceback
from pathlib import Path
import FreeCAD as App,FreeCADGui as Gui,OpenMatrix9Gui as OM
from PySide6 import QtCore
out=Path(os.environ['OM9_SMOKE_OUTPUT']);report=dict(module=OM.__file__,checks=[],observations=[])
sys.path.insert(0,os.environ['OM9_REPLAY_RETIREMENT_PROBE']);import OM9ReplayRetirement as probe
def state(doc):return dict(booked=doc.getBookedTransactionID(),pending=doc.HasPendingTransaction,undo=list(doc.UndoNames),redo=list(doc.RedoNames))
def check(name,value):report['checks'].append(dict(name=name,passed=bool(value)))
def run():
 try:
  Gui.activateWorkbench('OpenMatrix9Workbench')
  for action in ['value','close','remove','clear']:
   doc=App.newDocument('MergeDisposal');doc.UndoMode=1
   child=doc.getObject(probe.create(doc.Name));doc.recompute();doc.clearUndos()
   doc.openTransaction('Prior redo');child.Output='prior-redo';doc.commitTransaction();doc.undo()
   doc.openTransaction('Caller');before=state(doc);value=child.Value
   (out/'test-started.json').write_text(json.dumps(dict(action=action,before=before)))
   result=probe.run(doc.Name,action,'merge_open')
   check(action+' native open observer threw',result['open_callbacks']==1)
   check(action+' merge destructor callback ran and was blocked',result['callbacks']==1 and result['blocked']==1)
   check(action+' write rejected by replay barrier rather than illegal memory access','StaleGeometry'in result['blocked_error'])
   check(action+' rejection completes rollback cleanup',not result['accepted']and result['rollback']and result['complete'])
   check(action+' owner and original child remain alive',doc.Name in App.listDocuments()and doc.getObject('Child')is child)
   check(action+' native values restored and paired output cleared',child.Value==value and child.Output=='')
   check(action+' original caller booking and Redo unchanged',state(doc)==before)
   doc.abortTransaction();doc.redo()
   check(action+' original Redo remains executable',child.Output=='prior-redo')
   report['observations'].append(dict(action=action,result=result,before=before,after=state(doc)))
   App.closeDocument(doc.Name)
  report['ok']=all(c['passed']for c in report['checks'])
 except Exception:report['ok']=False;report['error']=traceback.format_exc()
 finally:
  (out/'results.json').write_text(json.dumps(report,indent=2))
  for name in list(App.listDocuments()):App.closeDocument(name)
  QtCore.QTimer.singleShot(100,Gui.getMainWindow().close)
QtCore.QTimer.singleShot(1000,run)
