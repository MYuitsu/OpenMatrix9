import FreeCAD as App,FreeCADGui as Gui
from PySide6 import QtCore,QtWidgets,QtGui,QtTest
from pathlib import Path
import os,json,traceback,sys,hashlib
sys.path.insert(0,str(Path(__file__).parent))
from command_console_support import command_input
out=Path(os.environ['OM9_SMOKE_OUTPUT']);config=json.loads(Path(os.environ['OM9_PHASE2_CASE']).read_text());report={'checks':[],'pid':os.getpid(),'macro_sha256':hashlib.sha256(Path(__file__).read_bytes()).hexdigest()}
def check(name,value):
    report['checks'].append({'name':name,'passed':bool(value)})
    if not value:raise AssertionError(name)
def settle():
    loop=QtCore.QEventLoop();QtCore.QTimer.singleShot(100,loop.quit);loop.exec();QtCore.QCoreApplication.sendPostedEvents(None,QtCore.QEvent.DeferredDelete)
def cmd(value):
    field.setText(value);QtTest.QTest.keyClick(field,QtCore.Qt.Key_Return);settle()
def edgefacts(edge):
    curve=edge.Curve
    if not hasattr(curve,'getWeights'):curve=edge.toNurbs().Edges[0].Curve
    return {'degree':curve.Degree,'weights':curve.getWeights(),'periodic':curve.isPeriodic(),
            'samples':[list(edge.valueAt(edge.FirstParameter+(edge.LastParameter-edge.FirstParameter)*i/32)) for i in range(33)],
            'start':list(edge.Vertexes[0].Point),'length':edge.Length,'valid':edge.isValid()}

def facts(obj):
    if len(obj.Shape.Edges)==1:return edgefacts(obj.Shape.Edges[0])
    segments=[edgefacts(e) for e in obj.Shape.Edges]
    return {'segments':segments,'length':sum(e['length'] for e in segments),'valid':obj.Shape.isValid()}

def equivalent(a,b):
    if isinstance(a,dict):return set(a)==set(b) and all(equivalent(a[k],b[k]) for k in a)
    if isinstance(a,list):return len(a)==len(b) and all(equivalent(x,y) for x,y in zip(a,b))
    if isinstance(a,float):return abs(a-b)<=1e-10
    return a==b
def run():
    global field
    try:
        import Part,ThreeDm,OpenMatrix9Gui as native
        Gui.activateWorkbench('OpenMatrix9Workbench');doc=App.newDocument('Phase2Rhino');doc.UndoMode=1
        objects=ThreeDm.import_file(config['input'],doc,mode='modeling');check('Rhino Export Selected imported owning curve',len(objects)==1)
        obj=objects[0];obj.Label='EditedCurve';basis=json.loads(native.curveBasis3dm(doc.Name,obj.Name))
        check('import preserves source periodic basis',basis['periodic']==config['source_periodic'])
        request=dict(basis);request['poles']=[p[:] for p in basis['poles']];request['poles'][1][1]+=0.25
        native.editModelingCurve3dm(doc.Name,obj.Name,json.dumps(request));doc.undo();doc.redo();check('imported curve CV Undo Redo',abs(json.loads(native.curveBasis3dm(doc.Name,obj.Name))['poles'][1][1]-request['poles'][1][1])<1e-9)
        weights=json.loads(native.curveBasis3dm(doc.Name,obj.Name));weights['weights'][1]*=1.1;native.editModelingCurve3dm(doc.Name,obj.Name,json.dumps(weights));check('explicit rational weight edit',abs(obj.Shape.Edges[0].Curve.getWeight(2)-weights['weights'][1])<1e-9)
        knots=json.loads(native.curveBasis3dm(doc.Name,obj.Name))
        if len(knots['knots'])>2:
            knots['knots'][1]=knots['knots'][0]+0.55*(knots['knots'][2]-knots['knots'][0])
            native.editModelingCurve3dm(doc.Name,obj.Name,json.dumps(knots));check('explicit ordered knot edit',abs(obj.Shape.Edges[0].Curve.getKnot(2)-knots['knots'][1])<1e-9)
        window=Gui.getMainWindow();field=command_input(window);settle()
        before=len(doc.Objects);cmd('InterpCrv');cmd('20,0,0');cmd('22,3,1');cmd('25,2,0');cmd('28,0,0');cmd('');new=doc.getObject('InterpCrv');new.Label='NewCurve'
        check('draw new native curve through CMD',new is not None and new.Shape.isValid() and len(doc.Objects)==before+1)
        cmd('InterpCrv');cmd('0,0,0');cmd('Cancel');check('curve Cancel no document mutation',len(doc.Objects)==before+1)
        # Rebuild imported current geometry through the same real command/dialog.
        existing={o.Name for o in doc.Objects}
        Gui.Selection.clearSelection();Gui.Selection.addSelection(obj);cmd('Rebuild')
        dialog=window.findChild(QtWidgets.QDialog,'OM9RebuildDialog');check('imported rational periodic placed curve Rebuild dialog',dialog is not None)
        dialog.findChild(QtWidgets.QSpinBox,'OM9RebuildPointCount').setValue(12);dialog.findChild(QtWidgets.QSpinBox,'OM9RebuildDegree').setValue(3);dialog.findChild(QtWidgets.QCheckBox,'OM9RebuildDeleteInput').setChecked(False)
        dialog.findChild(QtWidgets.QDialogButtonBox).button(QtWidgets.QDialogButtonBox.Ok).click();settle()
        rebuilt=next(o for o in doc.Objects if o.Name not in existing and hasattr(o,'Shape'));rebuilt.Label='RebuiltCurve'
        check('Rebuild native periodic flag and degree',rebuilt.Shape.Edges[0].Curve.Degree==3 and rebuilt.Shape.Edges[0].Curve.NbPoles==12)
        # Create a tail connected to the edited input's current endpoint, then Join.
        join_input=obj if not basis['periodic'] else new
        if basis['periodic']:
            loop_tail=doc.addObject('Part::Feature','LoopTail');end=obj.Shape.Edges[0].Vertexes[-1].Point;loop_tail.Shape=Part.makeLine(end,end+App.Vector(0,0,2));doc.recompute()
            count=len(doc.Objects);undos=len(doc.UndoNames);failed=False
            try:native.joinModelingCurves3dm(doc.Name,[obj.Name,loop_tail.Name])
            except (ValueError,RuntimeError):failed=True
            check('closed imported periodic Join rejected atomically',failed and len(doc.Objects)==count and len(doc.UndoNames)==undos)
            doc.removeObject(loop_tail.Name)
        end=join_input.Shape.Edges[0].Vertexes[-1].Point
        tail=doc.addObject('Part::Feature','Tail');tail.Shape=Part.makeLine(end,end+App.Vector(0,0,2));doc.recompute()
        joined_name=native.joinModelingCurves3dm(doc.Name,[join_input.Name,tail.Name]);joined=doc.getObject(joined_name);joined.Label='JoinedCurve'
        check('join current open curve with new curve',joined.Shape.isValid() and len(joined.Shape.Edges)==2)
        selected=[obj,new,rebuilt,joined];expected={o.Label:facts(o) for o in selected}
        fcstd=out/'phase2.FCStd';doc.saveAs(str(fcstd));name=doc.Name;App.closeDocument(name)
        source=Path(config['input']);disabled=source.with_suffix('.source-disabled');source.rename(disabled)
        try:
            check('owned source absent while reopening FCStd',not source.exists())
            doc=App.openDocument(str(fcstd));selected=[next(o for o in doc.Objects if o.Label==label) for label in expected]
        finally:disabled.rename(source)
        report['fcstd_expected']=expected;report['fcstd_restored']={o.Label:facts(o) for o in selected}
        check('FCStd preserves edited and new curves without source dependency',all(equivalent(facts(o),expected[o.Label]) for o in selected))
        output=out/'current-and-new-v5.3dm';ThreeDm.export_file(str(output),selected,modeling=True)
        report.update(ok=True,module=native.__file__,module_sha256=hashlib.sha256(Path(native.__file__).read_bytes()).hexdigest(),output=str(output),expected=expected)
    except Exception:report.update(ok=False,error=traceback.format_exc())
    (out/'results.json').write_text(json.dumps(report,indent=2))
    for name in list(App.listDocuments()):App.closeDocument(name)
    QtCore.QTimer.singleShot(100,Gui.getMainWindow().close)
QtCore.QTimer.singleShot(1000,run)
