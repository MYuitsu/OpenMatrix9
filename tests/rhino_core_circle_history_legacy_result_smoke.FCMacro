# SPDX-License-Identifier: LGPL-2.1-or-later
"""Legacy empty-recipe AroundCurve keeps explicit provenance and current result."""
import json,os,traceback
from pathlib import Path
import FreeCAD as App,FreeCADGui as Gui,Part,OpenMatrix9Gui as OM
from PySide6 import QtCore
out=Path(os.environ['OM9_SMOKE_OUTPUT']);report=dict(module=OM.__file__,checks=[])
def check(name,value):report['checks'].append(dict(name=name,passed=bool(value)))
def paired(child,n):
 try:
  result=json.loads(child.OM9GeometryResult);snapshot=result['output_snapshots'][0];master=Part.Shape();master.importBrepFromString(snapshot['geometry_data']['native_master']['payload'])
  return snapshot['unit_context_snapshot']==child.OM9UnitContext and result['operation']=='ReplayCircleHistory'and all(not s.isNull()and s.isValid()and s.isClosed()and isinstance(s.Edges[0].Curve,Part.Circle)and abs(s.Edges[0].Curve.Radius-2)<1e-7 and (s.Edges[0].Curve.Center-App.Vector(5*n,0,0)).Length<1e-7 for s in [child.Shape,master])
 except (ValueError,KeyError,IndexError,TypeError):return False
def run():
 try:
  Gui.activateWorkbench('OpenMatrix9Workbench');cold=os.environ.get('OM9_CIRCLE_LEGACY_ARCHIVES')
  if cold:
   directory=Path(cold);saved=json.loads((directory/'saved.json').read_text());doc=App.openDocument(str(directory/'Legacy.FCStd'));child=doc.getObject('LegacyCircle');source=doc.getObject('Source')
   check('legacy cold exact result bytes preserved',child.OM9GeometryResult==saved['raw']);check('legacy cold paired native master',child.Recorded and not child.Recipe and paired(child,4))
   source.Shape=Part.makeLine(App.Vector(),App.Vector(50,0,0));doc.recompute();check('legacy cold restored empty recipe updates native path',paired(child,5)and not child.Recipe)
  else:
   doc=App.newDocument('CircleLegacyResult');doc.UndoMode=1;OM.setUnitContext(doc.Name,1.,1.,.01,.001,.01);settings=doc.addObject('OpenMatrix9Gui::HistorySettings','OM9HistorySettings');settings.BrokenHistoryWarning=False
   source=doc.addObject('Part::Feature','Source');source.Shape=Part.makeLine(App.Vector(),App.Vector(10,0,0));child=doc.addObject('OpenMatrix9Gui::CircleHistory','LegacyCircle');child.SourceCurve=(source,['Edge1']);child.PathFraction=.5;child.Radius=2;child.Recorded=True;doc.recompute()
   check('legacy initial owned result pairs with native Circle',paired(child,1))
   value=json.loads(child.OM9GeometryResult);context=value['operation_context'];storage=value['input_snapshots'][0]['geometry_data']['history_storage']
   check('legacy explicitly retains absent original command evidence',not child.Recipe and context['storage']=='legacy_around_curve'and context['original_construction']==''and storage['original_command_events']=='unavailable_legacy_record')
   source.Shape=Part.makeLine(App.Vector(),App.Vector(20,0,0));doc.recompute();check('legacy path edit refreshes owned result',paired(child,2))
   settings.Update=False;frozen=child.OM9GeometryResult;source.Shape=Part.makeLine(App.Vector(),App.Vector(30,0,0));doc.recompute();check('legacy Update No keeps exact paired output bytes',paired(child,2)and child.OM9GeometryResult==frozen)
   settings.Update=True;doc.recompute();check('legacy first resume publishes current pair',paired(child,3))
   source.Shape=Part.Shape();doc.recompute();check('legacy invalid source clears both outputs',child.Shape.isNull()and not child.OM9GeometryResult)
   source.Shape=Part.makeLine(App.Vector(),App.Vector(40,0,0));doc.recompute();check('legacy valid source recovers same storage',paired(child,4)and not child.Recipe)
   doc.saveAs(str(out/'Legacy.FCStd'));(out/'saved.json').write_text(json.dumps(dict(raw=child.OM9GeometryResult)),encoding='utf-8');check('legacy saved recorded dependency remains linked',child.Recorded and child.SourceCurve[0]==source)
  report['ok']=all(c['passed']for c in report['checks'])
 except Exception:report['ok']=False;report['error']=traceback.format_exc()
 finally:
  for name in list(App.listDocuments()):App.closeDocument(name)
  (out/'results.json').write_text(json.dumps(report,indent=2),encoding='utf-8');QtCore.QTimer.singleShot(100,Gui.getMainWindow().close)
QtCore.QTimer.singleShot(1200,run)
