# SPDX-License-Identifier: LGPL-2.1-or-later
"""A rejected replay preserves native Redo links to its detached owned objects."""
import json, os, sys, traceback
from pathlib import Path
import FreeCAD as App, FreeCADGui as Gui, OpenMatrix9Gui as OM
from PySide6 import QtCore
out = Path(os.environ['OM9_SMOKE_OUTPUT'])
report = dict(module=OM.__file__, checks=[], observations=[])
sys.path.insert(0, os.environ['OM9_REPLAY_RETIREMENT_PROBE'])
import OM9ReplayRetirement as probe

def state(doc):
    return dict(booked=doc.getBookedTransactionID(), pending=doc.HasPendingTransaction,
                undo=list(doc.UndoNames), redo=list(doc.RedoNames))

def check(name, value):
    report['checks'].append(dict(name=name, passed=bool(value)))

def run():
    try:
        Gui.activateWorkbench('OpenMatrix9Workbench')
        for kind in ['PropertyLink', 'PropertyLinkSub', 'PropertyLinkList', 'PropertyLinkSubList']:
            for action in ['value', 'close', 'remove', 'clear']:
                label = kind + ' ' + action
                doc = App.newDocument('RedoLinks')
                doc.UndoMode = 1
                child = doc.getObject(probe.create(doc.Name))
                child.addProperty('App::' + kind, 'Linked')
                doc.recompute()
                doc.clearUndos()
                doc.openTransaction('Prior linked creation')
                target = doc.addObject('App::FeaturePython', 'Target')
                expected = dict(PropertyLink=target, PropertyLinkSub=(target, ['Face1', 'Edge2']),
                                PropertyLinkList=[target], PropertyLinkSubList=[(target, ('Face1', 'Edge2'))])[kind]
                child.Linked = expected
                child.Value = 'prior-redo-value'
                doc.commitTransaction()
                doc.undo()
                check(label + ' fixture has Redo owning detached target',
                      doc.getObject('Target') is None and len(doc.RedoNames) == 1)
                doc.openTransaction('Caller')
                before = state(doc)
                value = child.Value
                result = probe.run(doc.Name, action, 'discarded_redo')
                check(label + ' retired property callback is blocked',
                      result['callbacks'] == 1 and result['blocked'] == 1)
                check(label + ' rejection completes rollback and cleanup',
                      not result['accepted'] and result['rollback'] and result['complete'])
                check(label + ' caller booking and Redo are unchanged', state(doc) == before)
                check(label + ' replay values are restored', child.Value == value and child.Output == '')
                doc.abortTransaction()
                doc.redo()
                check(label + ' native Redo restores same target identity', doc.getObject('Target') is target)
                check(label + ' native Redo restores linked target and subnames', child.Linked == expected)
                check(label + ' native Redo restores paired value', child.Value == 'prior-redo-value')
                report['observations'].append(dict(kind=kind, action=action, result=result,
                                                  linked=str(child.Linked), expected=str(expected)))
                App.closeDocument(doc.Name)
        report['ok'] = all(c['passed'] for c in report['checks'])
    except Exception:
        report['ok'] = False
        report['error'] = traceback.format_exc()
    finally:
        (out / 'results.json').write_text(json.dumps(report, indent=2))
        for name in list(App.listDocuments()):
            App.closeDocument(name)
        QtCore.QTimer.singleShot(100, Gui.getMainWindow().close)
QtCore.QTimer.singleShot(1000, run)
